Attribute VB_Name = "Aloitus"
' --- 64-bitti korjattu: PtrSafe lisatty kaikkiin Declare-lauseisiin ---
' --------- [ CHOOSE FILE ] -----------------
Declare PtrSafe Function GetOpenFileName Lib "comdlg32.dll" Alias "GetOpenFileNameA" (pOpenfilename As OPENFILENAME) As Long
Declare PtrSafe Function FindWindow Lib "User32" Alias "FindWindowA" (ByVal lpClassName As Any, ByVal lpWindowName As Any) As LongPtr
Public Type OPENFILENAME
    lStructSize As Long
    hwndOwner As LongPtr
    hInstance As LongPtr
    lpstrFilter As String
    lpstrCustomFilter As String
    nMaxCustFilter As Long
    nFilterIndex As Long
    lpstrFile As String
    nMaxFile As Long
    lpstrFileTitle As String
    nMaxFileTitle As Long
    lpstrInitialDir As String
    lpstrTitle As String
    flags As Long
    nFileOffset As Integer
    nFileExtension As Integer
    lpstrDefExt As String
    lCustData As Long
    lpfnHook As Long
    lpTemplateName As String
End Type
Public DB As New ADODB.Connection
Public TauluMotors As New ADODB.Recordset
Public Tietokanta As String
Public StartOK As Boolean

Attribute VB_Name = "ApuForm"
Attribute VB_Base = "0{093D6E80-3CA9-4402-B5FF-EEB1F024F916}{2602D6B1-CACA-4EAB-85B4-627B1DE47ACF}"
Attribute VB_GlobalNameSpace = False
Attribute VB_Creatable = False
Attribute VB_PredeclaredId = True
Attribute VB_Exposed = False
Attribute VB_TemplateDerived = False
Attribute VB_Customizable = False






Private Sub CommandButton2_Click()
  AppActivate Application.Caption 'Vain tällä tavoin voidaan katkaista mahdollinen Zoom komento
  SendKeys "{Esc}{Esc}", True
  ApuForm.Hide
  MainForm.Show
End Sub

Attribute VB_Name = "MainForm"
Attribute VB_Base = "0{C23DCFD1-2B71-46CA-A8AA-394FFA544226}{B53C2B3C-BA9B-47C5-BF4D-319816212B6E}"
Attribute VB_GlobalNameSpace = False
Attribute VB_Creatable = False
Attribute VB_PredeclaredId = True
Attribute VB_Exposed = False
Attribute VB_TemplateDerived = False
Attribute VB_Customizable = False

Private Sub Lisays_Click()
Dim oBlock As AcadBlockReference
Dim BName As String
Dim iPoint(2) As Double
Dim gPoint As Variant
Dim Attribuutit As Variant
Dim i As Integer
Dim Piste As String
Dim aTAG As AcadAttributeReference
Dim aNAME As AcadAttributeReference
Dim aI1 As AcadAttributeReference
Dim aI2 As AcadAttributeReference
Dim aI3 As AcadAttributeReference
Dim P1 As Variant
Dim P2 As Variant
Dim P3 As Variant
Dim P4 As Variant
Dim Pisteet(9) As Double
Dim Pisteet2(9) As Double
Dim Pisteet3(9) As Double
Dim Pisteet4(9) As Double
Dim ValiTeksti As AcadText

'Liitetään ensin blokki kuvaan
  MainForm.Hide
  ThisDrawing.SendCommand Chr(27) & Chr(27) 'Varmistetaan että ollaan poistuttu komennosta
 ' ThisDrawing.ActiveLayer = ThisDrawing.Layers(TLAYER.Value)
  ThisDrawing.ActiveLayer = ThisDrawing.Layers("INST")
'Snap tila ja grid päälle
  ThisDrawing.ActiveViewport.SetSnapSpacing 1.25, 1.25
  ThisDrawing.ActiveViewport.SetGridSpacing 2.5, 2.5
  ThisDrawing.ActiveViewport.SnapOn = True
  ThisDrawing.ActiveViewport.GridOn = True
    
  gPoint = ThisDrawing.Utility.GetPoint(, "Set Motor position")
  iPoint(0) = gPoint(0) + 0.00001
  iPoint(1) = gPoint(1) + 0.00001
'---------------------------------------------------------
  Piste = DoubleToPoint(CDbl(iPoint(0))) & "," & DoubleToPoint(CDbl(iPoint(1)))
  BName = "MOTORTAG"
'Insertoidaan blokki
  Set oBlock = ThisDrawing.ModelSpace.InsertBlock(iPoint, BName, 1, 1, 1, 0)
'Pyydetään siirtämään blokki haluttuun paikkaa
  ThisDrawing.SendCommand "(command ""move"" ""last"" """" """ & Piste & """)" & vbCr
  With oBlock
    If .InsertionPoint(0) = iPoint(0) And .InsertionPoint(1) = iPoint(1) Then
      .Delete
      GoTo Loppu
    End If
  End With
'Haetaan Siirrettävät attribuutit muistiin
  Attribuutit = oBlock.GetAttributes
  For i = 0 To UBound(Attribuutit)
    Select Case UCase(Attribuutit(i).TagString)
      Case "TAG"
        Set aTAG = Attribuutit(i)
      Case "NAME"
        Set aNAME = Attribuutit(i)
      Case "I1"
        Set aI1 = Attribuutit(i)
      Case "I2"
        Set aI2 = Attribuutit(i)
      Case "REV"
        Case "I3"
        Set aI3 = Attribuutit(i)
    End Select
  Next i
'Lisätään "valeTAG" kuvaan
  Set ValiTeksti = ThisDrawing.ModelSpace.AddText(Arvo(Moottorit.Column(0, Moottorit.ListIndex)), aTAG.InsertionPoint, 2.5)
  Piste = DoubleToPoint(CDbl(ValiTeksti.InsertionPoint(0))) & "," & DoubleToPoint(CDbl(ValiTeksti.InsertionPoint(1)))
'Pyydetään siirtämään se oikeaan paikkaan
  ThisDrawing.Utility.Prompt "Set TAG postion"
  ThisDrawing.SendCommand "(command ""move"" ""last"" """" """ & Piste & """)" & vbCr
'Täytetään Attribuutit valituilla arvoilla
  For i = 0 To UBound(Attribuutit)
    Select Case UCase(Attribuutit(i).TagString)
      Case "TAG"
        Set aTAG = Attribuutit(i)
        aTAG.TextString = Arvo(Moottorit.Column(0, Moottorit.ListIndex))
      Case "NAME"
        Set aNAME = Attribuutit(i)
        aNAME.TextString = Arvo(Moottorit.Column(1, Moottorit.ListIndex))
      'Case "RPM"
        'Set aRPM = Attribuutit(i)
        'aRPM.TextString = Arvo(Moottorit.Column(2, Moottorit.ListIndex))
      'Case "KW"
        'Set aKW = Attribuutit(i)
        'aKW.TextString = Arvo(Moottorit.Column(3, Moottorit.ListIndex))
      Case "REV"
        'Attribuutit(i).TextString = Arvo(Moottorit.Column(4, Moottorit.ListIndex))
      Case "FC"
        'Attribuutit(i).TextString = Arvo(Moottorit.Column(5, Moottorit.ListIndex))
    End Select
  Next i
'Siirretään Tag ja muut Attribuutit Tagin alle sovitulle etäisyydelle
  iPoint(0) = ValiTeksti.InsertionPoint(0)
  iPoint(1) = ValiTeksti.InsertionPoint(1)
  aTAG.InsertionPoint = iPoint
  iPoint(1) = iPoint(1) + 4.75
  aNAME.InsertionPoint = iPoint
  iPoint(1) = iPoint(1) - 9
  aI1.InsertionPoint = iPoint
  iPoint(1) = iPoint(1) - 4.5
  aI2.InsertionPoint = iPoint
  iPoint(1) = iPoint(1) - 4.5
  aI3.InsertionPoint = iPoint
  ValiTeksti.Delete
'Piirretään laatikko tagin ympärille, sekä viiva
  aTAG.GetBoundingBox P1, P2
  P1(0) = P1(0) - 1
  P1(1) = P1(1) - 1
  P2(0) = P2(0) + 1
  P2(1) = P2(1) + 1
  Pisteet(0) = P1(0): Pisteet(1) = P1(1)
  Pisteet(2) = P1(0): Pisteet(3) = P2(1)
  Pisteet(4) = P2(0): Pisteet(5) = P2(1)
  Pisteet(6) = P2(0): Pisteet(7) = P1(1)
  Pisteet(8) = P1(0): Pisteet(9) = P1(1)
  ThisDrawing.ModelSpace.AddLightWeightPolyline Pisteet
  
  '  aKW.GetBoundingBox P3, P4
  'P3(0) = P3(0) - 1
  'P3(1) = P3(1) - 1
  'P4(0) = P4(0) + 1
  'P4(1) = P4(1) + 1
  Pisteet2(0) = P1(0): Pisteet2(1) = P1(1) - 4.5
  Pisteet2(2) = P1(0): Pisteet2(3) = P2(1) - 4.5
  Pisteet2(4) = P2(0): Pisteet2(5) = P2(1) - 4.5
  Pisteet2(6) = P2(0): Pisteet2(7) = P1(1) - 4.5
  Pisteet2(8) = P1(0): Pisteet2(9) = P1(1) - 4.5
  ThisDrawing.ModelSpace.AddLightWeightPolyline Pisteet2
  
  Pisteet3(0) = P1(0): Pisteet3(1) = P1(1) - 9
  Pisteet3(2) = P1(0): Pisteet3(3) = P2(1) - 9
  Pisteet3(4) = P2(0): Pisteet3(5) = P2(1) - 9
  Pisteet3(6) = P2(0): Pisteet3(7) = P1(1) - 9
  Pisteet3(8) = P1(0): Pisteet3(9) = P1(1) - 9
  ThisDrawing.ModelSpace.AddLightWeightPolyline Pisteet3
  
  Pisteet4(0) = P1(0): Pisteet4(1) = P1(1) - 13.5
  Pisteet4(2) = P1(0): Pisteet4(3) = P2(1) - 13.5
  Pisteet4(4) = P2(0): Pisteet4(5) = P2(1) - 13.5
  Pisteet4(6) = P2(0): Pisteet4(7) = P1(1) - 13.5
  Pisteet4(8) = P1(0): Pisteet4(9) = P1(1) - 13.5
  ThisDrawing.ModelSpace.AddLightWeightPolyline Pisteet4
  

  'If P1(1) < oBlock.InsertionPoint(1) + 5 Then 'Alapuolella
  '  P1(1) = P2(1)
  'End If
  'If P2(0) < oBlock.InsertionPoint(0) - 5 Then 'Vasemmalla
  '  P1(0) = P2(0)
  '  P2(0) = oBlock.InsertionPoint(0) - 5
  'ElseIf P1(0) > oBlock.InsertionPoint(0) + 5 Then 'Oikealla puolella
  '  P2(0) = oBlock.InsertionPoint(0) + 5
  'ElseIf P1(0) < oBlock.InsertionPoint(0) - 5 Then 'Vasemmalla puolella vähän
  '  P2(0) = oBlock.InsertionPoint(0) - 5
  'Else
  '  P1(0) = P2(0)
  '  P2(0) = oBlock.InsertionPoint(0) + 5
  'End If
  'P2(1) = oBlock.InsertionPoint(1) + 5
  'ThisDrawing.ModelSpace.AddLine P1, P2
  'ThisDrawing.Regen acActiveViewport
'Piirretään viiva blokin ja näytetyn moottorin paikan välille
  If gPoint(1) > oBlock.InsertionPoint(1) Then  'Yläpuolella
    P2(0) = oBlock.InsertionPoint(0)
    P2(1) = oBlock.InsertionPoint(1) + 10
  Else
    P2(0) = oBlock.InsertionPoint(0)
    P2(1) = oBlock.InsertionPoint(1)
  End If
  ThisDrawing.ModelSpace.AddLine gPoint, P2
  'ThisDrawing.ModelSpace.AddCircle gPoint, 1
  ThisDrawing.Regen acActiveViewport
Loppu:
  Set oBlock = Nothing
  MainForm.Show
End Sub

Private Sub Moottorit_Click()

End Sub

Private Sub MuokkaaKuvaa_Click()
  MainForm.Hide
  ApuForm.Show
End Sub
Private Function DoubleToPoint(ByVal Piste As Double) As String
Dim APU As String
Dim Osoitin As Integer
  APU = CStr(Piste)
  Osoitin = InStr(APU, ",")
  If Osoitin = 0 Then
    DoubleToPoint = APU
  Else
    DoubleToPoint = Left(APU, Osoitin - 1) & "." & Mid(APU, Osoitin + 1)
  End If
End Function
Private Function Arvo(Tieto As Variant) As String
  If IsNull(Tieto) Or Tieto = vbNullString Then
    Arvo = vbNullChar
  Else
    Arvo = Tieto
  End If
End Function
Private Sub UserForm_Initialize()
Dim i As Integer
  For i = 0 To ThisDrawing.Layers.Count - 1
    TLAYER.AddItem ThisDrawing.Layers(i).Name
  Next i
  TLAYER.Value = ThisDrawing.ActiveLayer.Name
  TaytaLaitteet
End Sub
Private Sub TaytaLaitteet()
Moottorit.Clear
TauluMotors.Requery
If TauluMotors.EOF = False Then
  Moottorit.Column() = TauluMotors.GetRows()
  Moottorit.ListIndex = 0
End If
End Sub

Attribute VB_Name = "StartForm"
Attribute VB_Base = "0{95DB4D55-769F-47AC-A3AD-E212DAD3FEA5}{D6088AC1-8E26-4757-90EF-4D8FCBF1B9F9}"
Attribute VB_GlobalNameSpace = False
Attribute VB_Creatable = False
Attribute VB_PredeclaredId = True
Attribute VB_Exposed = False
Attribute VB_TemplateDerived = False
Attribute VB_Customizable = False


Private Sub CommandButton1_Click()
  If Dir(Tietokannat.Value) <> "" Then
    DB.Open "Driver=Microsoft Access Driver (*.mdb);DBQ=" & Tietokannat.Value & ";"
    Tietokanta = Tietokannat.Value
    On Error GoTo Virhe
    Set TauluMotors = DB.Execute("Select * From TOACAD_MotTAG")
    StartOK = True
    Unload Me
    Exit Sub
Virhe:
    Tietokannat.BackColor = RGB(255, 150, 150)
    MsgBox "Database: " & vbCrLf & Tietokannat.Value & vbCrLf & _
           "did not contain necessary query (TOACAD_MotTAG)!", vbCritical, "Error!"
    Tietokannat.SetFocus
    Err.Clear
    Set TAULU = Nothing
    Exit Sub
  Else 'Tietokantaa ei löytynyt
    Tietokannat.BackColor = RGB(255, 150, 150)
    MsgBox "Database: " & vbCrLf & Tietokannat.Value & vbCrLf & "did not found!", vbCritical, "Error!"
    Tietokannat.SetFocus
  End If
End Sub
Private Sub CommandButton2_Click()
  Set DB = Nothing
  Unload Me
End Sub
Private Sub CommandButton3_Click()
'Tämä valitsee tiedoston hakemistosta
    Dim OpenFile As OPENFILENAME
    Dim lReturn As Long
    Dim Filtteri As String
    Dim AHakem As String
    Dim Otsikko As String
    Dim WHandle As Long
    
    WHandle = FindWindow(0&, "Motor TAG Insertion")
    AHakem = "L:\"
    
    Filtteri = "MS Access Database (*.mdb)" & Chr(0) & "*.MDB" & Chr(0)
    Otsikko = "Choose Database"
    With OpenFile
      .lStructSize = Len(OpenFile)
      .hwndOwner = WHandle
      .hInstance = 0
      .lpstrFilter = Filtteri
      .nFilterIndex = 1
      .lpstrFile = String(257, 0)
      .nMaxFile = Len(.lpstrFile) - 1
      .lpstrFileTitle = .lpstrFile
      .nMaxFileTitle = .nMaxFile
      .lpstrInitialDir = AHakem
      .lpstrTitle = Otsikko
      .flags = 0
    End With
    lReturn = GetOpenFileName(OpenFile)
    If lReturn = 0 Then
        'Painettiin Cancel painiketta. Ei tehdä mitään
    Else 'Otetaan ylös Tiedostonimi ja Hakemisto
      Tietokannat.AddItem Mid(OpenFile.lpstrFile, 1, InStr(OpenFile.lpstrFile, Chr(0)) - 1)
      Tietokannat.ListIndex = Tietokannat.ListCount - 1
    End If
End Sub
Private Sub UserForm_Initialize()
  Tietokannat.AddItem "N:\whldata\Projekti\Santa Fe 220018\DATABASE\MAINEQ.mdb"
  Tietokannat.ListIndex = 0
End Sub
