Attribute VB_Name = "ApuForm"
Attribute VB_Base = "0{001ABBC7-F5F1-4FB7-9E34-901082107A02}{45386D3E-267A-4C5D-A615-A49E6ACB60B9}"
Attribute VB_GlobalNameSpace = False
Attribute VB_Creatable = False
Attribute VB_PredeclaredId = True
Attribute VB_Exposed = False
Attribute VB_TemplateDerived = False
Attribute VB_Customizable = False


Private Sub CommandButton2_Click()
  AppActivate Application.Caption 'Vain tällä tavoin voidaan katkaista mahdollinen Zoom komento
  SendKeys "{Esc}{Esc}", True
  ApuForm.Hide
  MainForm.Show
End Sub

Attribute VB_Name = "MainForm"
Attribute VB_Base = "0{FC396067-DA32-4C1B-9971-8AD269961B01}{68E4CA8E-D727-48A7-AC39-2228BD506E38}"
Attribute VB_GlobalNameSpace = False
Attribute VB_Creatable = False
Attribute VB_PredeclaredId = True
Attribute VB_Exposed = False
Attribute VB_TemplateDerived = False
Attribute VB_Customizable = False

Dim TFiltter As String
Private Sub AreaJarj_Click()
  Jarjesta
End Sub

Private Sub LoopJarj_Click()
  Jarjesta
End Sub
Private Sub Filtteri_Click()
  If Filtteri.Value = True Then
    TFiltter = InputBox("Give filtter for INSTTAG. Eg. ""*3102*""." & vbCrLf & "Or press Cancel to clear filtter.", "Give Filtter", TFiltter)
  End If
  Jarjesta
End Sub
Private Sub Jarjesta()
Dim Sortti As String
Dim Missa As String
If AreaJarj.Value = True And LoopJarj.Value = True Then
  Sortti = "AreaCode, LoopNo"
ElseIf AreaJarj.Value = True Then
  Sortti = "AreaCode"
ElseIf LoopJarj.Value = True Then
  Sortti = "LoopNo"
End If
If Filtteri.Value = True Then
  If TFiltter <> "" Then
    Missa = "INSTTAG Like '" & TFiltter & "' "
    Missa = Replace(Missa, "*", "%")
    Missa = Replace(Missa, "?", "#")
  End If
End If
  TauluLoops.Sort = Sortti
  TauluLoops.Filter = Missa
  TauluMotors.Sort = Sortti
  TauluMotors.Filter = Missa
  TaytaLaitteet
End Sub
Private Sub Lisays_Click() 'Laitteen insertointi
Dim oBlock As AcadBlockReference
Dim oDot As AcadLWPolyline
Dim Viiva As AcadLine
Dim PViiva As AcadPolyline
Dim ipoint As Variant
Dim ePoint As Variant
Dim bPoint As Variant
Dim BName As String
Dim Attribuutit As Variant
Dim i As Integer
Dim Piste As String
Dim PLPisteet(0 To 5) As Double
Dim aPoint(2) As Double
Dim Lisatty As Boolean
Dim Kulma As Double
'Liitetään ensin piste
On Error Resume Next
  MainForm.Hide
  ThisDrawing.ActiveLayer = ThisDrawing.Layers(TLAYER.Value)
  ipoint = ThisDrawing.Utility.GetPoint(, "Set point")
  If OBLoop.Value = True Then
    BName = "LOOPBLOCK2.dwg"
  Else
    BName = "MOTORBLOCK2.dwg"
    Set oDot = AddDonut(ThisDrawing.ModelSpace, 0, 330 * TScale.Value, ipoint)
    oDot.Color = acYellow
'    Set oDot = ThisDrawing.ModelSpace.InsertBlock(ipoint, BName, TScale.Value, TScale.Value, 1, 0)
  End If
  If Err <> 0 Then GoTo Loppu
'Liitetään sitten positioblokki
  Set oBlock = ThisDrawing.ModelSpace.InsertBlock(ipoint, BName, TScale.Value, TScale.Value, 1, 0)
  If Err <> 0 Then GoTo Loppu
'Vaihdetaan positioblokin  attribuutit
  Attribuutit = oBlock.GetAttributes
  For i = 0 To UBound(Attribuutit) 'Käydään läpi kaikki attribuutit
    With Attribuutit(i)
      If .TagString = "INSTTAG" Then
        .TextString = Left(TINSTTAG.Value, InStr(TINSTTAG.Value, "-") - 1)
      ElseIf .TagString = "INSTPOS" Then
        .TextString = Mid(TINSTTAG.Value, InStr(TINSTTAG.Value, "-") + 1)
      ElseIf .TagString = "MOTORTAG" Then
        .TextString = Arvo(TINSTTAG.Value)
      ElseIf .TagString = "HEIGHT" Then
        .TextString = Arvo(THEIGHT1 & THEIGHT2 & " " & THEIGHT3)
      ElseIf .TagString = "BOX" Or .TagString = "CABLE" Then
        .TextString = Arvo(TBOX.Value)
      ElseIf UCase(.TagString) = "POSX" Then
        .TextString = CStr(ipoint(0))
      ElseIf UCase(.TagString) = "POWER" Then
        .TextString = TPOWER.Value
      ElseIf UCase(.TagString) = "POSY" Then
        .TextString = CStr(ipoint(1))
      ElseIf UCase(.TagString) = "POINTHNDL" Then
        .TextString = oDot.Handle
      ElseIf Left(.TagString, 1) = "@" Then
        .TextString = Arvo(Controls("A" & Mid(.TagString, 2)).Value)
      End If
    End With
  Next i
  Piste = DoubleToPoint(CDbl(ipoint(0))) & "," & DoubleToPoint(CDbl(ipoint(1)))
'Annetaan komentorivikomento jolla saadaan siirrettyä blokkia haluttuun paikkaan
  ThisDrawing.SendCommand "(command ""move"" ""last"" """" """ & Piste & """)" & vbCr
'Tarkistetaan että blokkia yleensä siirettiin
  With oBlock
    If .InsertionPoint(0) = ipoint(0) And .InsertionPoint(1) = ipoint(1) Then 'Ei siirretty joten poistetaan blokki
      .Delete
      If OBLoop.Value = False Then oDot.Delete
      GoTo Loppu
    End If
  End With
'Piirretään viiva
  Lisatty = True
  If OBLoop.Value = True Then
    aPoint(0) = oBlock.InsertionPoint(0)
    aPoint(1) = oBlock.InsertionPoint(1)
    Kulma = ThisDrawing.Utility.AngleFromXAxis(aPoint, ipoint)
    ePoint = ThisDrawing.Utility.PolarPoint(aPoint, Kulma, 300 * TScale.Value)
    Set Viiva = ThisDrawing.ModelSpace.AddLine(ipoint, ePoint)
    bPoint = ThisDrawing.Utility.PolarPoint(ipoint, Kulma - 3.14159, 200 * TScale.Value)
    PLPisteet(0) = ipoint(0): PLPisteet(1) = ipoint(1)
    PLPisteet(3) = bPoint(0): PLPisteet(4) = bPoint(1)
    Set PViiva = ThisDrawing.ModelSpace.AddPolyline(PLPisteet)
    Viiva.Color = acYellow
    PViiva.SetWidth 0, 0, 100 * TScale.Value
    PViiva.Color = acYellow
  Else
    Do
      ePoint = ThisDrawing.Utility.GetPoint(ipoint, "Draw line")
      If Err <> 0 Then
        If Viiva Is Nothing Then 'Lopetettiin ennen kuin yhtäkään viiva oli piirretty
          'oDot.Delete   'Tuhotaan piste, koska sitä ei tarvita
          GoTo Loppu
        End If
        Err.Clear
        Exit Do
      Else
        Set Viiva = ThisDrawing.ModelSpace.AddLine(ipoint, ePoint)
        Viiva.Color = acYellow
        ipoint(0) = ePoint(0)
        ipoint(1) = ePoint(1)
      End If
    Loop
  End If
  Set Viiva = Nothing
  Set PViiva = Nothing
'Asetetaan indeksi yhtä suuremmaksi
On Error GoTo 0
If Lisatty Then
  TauluINSTTAG.AddNew
    TauluINSTTAG.Fields("INSTTAG").Value = TINSTTAG.Value
    TauluINSTTAG.Fields("DWG").Value = ThisDrawing.Name
  TauluINSTTAG.Update
  TaytaLaitteet
End If
Loppu:
  Set oBlock = Nothing
  Set oDot = Nothing
  Err.Clear
  MainForm.Show
End Sub
Private Sub Lisays_KeyPress(ByVal KeyAscii As MSForms.ReturnInteger)
  MsgBox KeyAscii
End Sub
Private Sub LoopLaitteet_Change()
Dim Lista As Variant
Dim i As Integer
  With LoopLaitteet
    If IsNull(.Value) = False Then
      If .ListIndex >= 0 Then
        TINSTTAG.Value = .Column(0, .ListIndex)
      End If
    End If
  End With
End Sub
Private Sub MotorLaitteet_Change()
  If IsNull(MotorLaitteet.Value) = False Then
    With MotorLaitteet
      If .ListIndex >= 0 Then
        TINSTTAG.Value = .Column(0, .ListIndex)
        TPOWER.Value = .Column(5, .ListIndex)
      End If
    End With
  End If
End Sub

Private Sub Nakymat_Change()
If Nakymat.Value <> "" Then
  Dim XDataOut As Variant
  Dim XTypeOut As Variant
  Dim i As Integer
  ThisDrawing.Views(Nakymat.Value).GetXData "POSITIONING", XTypeOut, XDataOut
  If IsEmpty(XTypeOut) = False Then
    For i = LBound(XTypeOut) To UBound(XTypeOut)
      If XTypeOut(i) = 1040 Then
        VOffset.Value = Replace(XDataOut(i), ".", ",")
      End If
    Next i
  Else
    VOffset.Value = ""
  End If
End If
End Sub

Private Sub OBLoop_Click()
  LoopLaitteet.Visible = True
  MotorLaitteet.Visible = False
  LBoxCabel.Caption = "Box:"
  LoopLaitteet_Change
 
End Sub
Private Sub OBMotor_Click()
  LoopLaitteet.Visible = False
  MotorLaitteet.Visible = True
  LBoxCabel.Caption = "Cabel:"
  MotorLaitteet_Change
End Sub
Private Sub CTScale_Change()
  TScale.Value = Replace(CTScale.Value * 0.001, ".", ",")
End Sub
Private Sub PoimiKork_Click()
Dim Piste As Variant
Dim Nakyma As AcadView
Dim ViewportObj As AcadViewport
Set ViewportObj = ThisDrawing.ActiveViewport

If VOffset.Value = "" Then
  MsgBox "Set offset first!", vbInformation, "Pick up point"
Else
  'Piilotetaan formi jotta päästään käsiksi AutoCADiin
  MainForm.Hide
  'Talletetaan nykyinen näkymä
  ThisDrawing.SendCommand "-view s apu_curv" & vbCrLf
  'Zoomatan haluttuun näkymään
  Set Nakyma = ThisDrawing.Views(Nakymat.Value)
  ViewportObj.SetView Nakyma
  ThisDrawing.ActiveViewport = ViewportObj
  On Error GoTo Virhe
  'Pyydetään poimimaan piste
  Piste = ThisDrawing.Utility.GetPoint(, "Pick up point")
'Asetetaan korkeus poimitun pisteen mukaan
  THEIGHT2.Value = Round((VOffset.Value + Piste(1) * CDbl(Replace(TRatio.Value, ".", ","))), 2)
Virhe:
'Zoomataan aloitusnäkymään
  Set Nakyma = ThisDrawing.Views("apu_curv")
  ViewportObj.SetView Nakyma
  ThisDrawing.ActiveViewport = ViewportObj
  Nakyma.Delete
  Err.Clear
  MainForm.Show
End If
Set ViewportObj = Nothing
Set Nakyma = Nothing
End Sub
Private Sub TRatio_MouseDown(ByVal Button As Integer, ByVal Shift As Integer, ByVal X As Single, ByVal Y As Single)
Dim xtype(0 To 1) As Integer
Dim XData(0 To 1) As Variant
Dim Ohjelma As AcadRegisteredApplication
  
  Dim Ratio As String
  Dim RatioArvo As Double
  Ratio = TRatio.Value
'Pyydetään ratio käyttäjältä
  Ratio = InputBox("Give Ratio for current drawing.", "Set Ratio", Ratio)
  If Ratio <> "" Then
    RatioArvo = CDbl(Replace(Ratio, ".", ","))
    TRatio.Value = CStr(OffsetRatio)
    xtype(0) = 1001: XData(0) = "POSITIONING"
    xtype(1) = 1040: XData(1) = RatioArvo
    On Error GoTo Virhe
'Haetaan ohjelma, johon tieto liitetään
    Set Ohjelma = ThisDrawing.RegisteredApplications("POSITIONING")
Virhe:
    If Err <> 0 Then 'Ohjelmaa ei ollut, joten lisätään se
      Err.Clear
      Set Ohjelma = ThisDrawing.RegisteredApplications.Add("POSITIONING")
    End If
'Talletaan Ration kuvaan
    Ohjelma.SetXData xtype, XData
    TRatio.Value = CStr(RatioArvo)
  End If
End Sub
Private Sub TScale_AfterUpdate()
  If TScale.Value = 0 Or TScale.Value = "" Then
    TScale.Value = 1
  ElseIf CDbl(TScale.Value) > 4 Then
    TScale.Value = 4
  End If
  CTScale.Value = TScale.Value * 1000
End Sub
Private Sub TScale_KeyPress(ByVal KeyAscii As MSForms.ReturnInteger)
  If KeyAscii > 47 And KeyAscii < 58 Then
  ElseIf KeyAscii = 44 Or 46 Then   'pilkku = 44, piste=46
    If InStr(TScale.Value, ",") Then
      KeyAscii = 0
    Else
      KeyAscii = 44
    End If
  Else
    KeyAscii = 0
  End If
End Sub
Private Sub UserForm_Activate()
Dim i As Integer
If ThisDrawing.Views.Count > Nakymat.ListCount Then
  Nakymat.Clear
  For i = 0 To ThisDrawing.Views.Count - 1
    Nakymat.AddItem ThisDrawing.Views(i).Name
  Next i
  Nakymat.ListIndex = 0
End If
End Sub
Private Sub UserForm_Initialize()
Dim i As Integer
Dim Ohjelma As AcadRegisteredApplication
Dim XDataType As Variant
Dim XDataValue As Variant
  On Error GoTo Virhe
  Set Ohjelma = ThisDrawing.RegisteredApplications("POSITIONING")
  Ohjelma.GetXData "POSITIONING", XDataType, XDataValue
  TRatio.Value = Replace(XDataValue(1), ".", ",")
  Set Ohjelma = Nothing
  GoTo OK
Virhe:
  Err.Clear
  TRatio.Value = "1"
OK:
  TauluLoops.Open "SELECT INSTTAG, DESCRIPTION, DWG, AreaCode, LoopNo FROM _ForAcadLoops", DB ', adOpenDynamic
  TauluMotors.Open "SELECT  INSTTAG, DESCRIPTION, DWG, AreaCode, LoopNo, Power FROM _ForAcadMotors", DB ', adOpenDynamic
  TauluINSTTAG.Open "_InsertedToAcad", DB, adOpenStatic, adLockOptimistic
  For i = 0 To ThisDrawing.Layers.Count - 1
    TLAYER.AddItem ThisDrawing.Layers(i).Name
  Next i
  TLAYER.Value = ThisDrawing.ActiveLayer.Name
  TaytaLaitteet
End Sub
Private Sub StopButton_Click() 'Ohjelman suorituksen keskeytys
  Unload Me
End Sub
Private Sub UserForm_Terminate()
  Set DB = Nothing
  Set TauluLoops = Nothing
  Set TauluMotors = Nothing
  Set TauluINSTTAG = Nothing
End Sub
Private Sub TaytaLaitteet()
LoopLaitteet.Clear
MotorLaitteet.Clear
TauluMotors.Requery
TauluLoops.Requery
If TauluMotors.EOF = False Then
  MotorLaitteet.Column() = TauluMotors.GetRows()
  MotorLaitteet.ListIndex = 0
End If
If TauluLoops.EOF = False Then
  LoopLaitteet.Column() = TauluLoops.GetRows()
  LoopLaitteet.ListIndex = 0
End If
End Sub
Private Sub CommandButton2_Click()
  MainForm.Hide
  ApuForm.Show
End Sub
Private Function Arvo(Tieto As Variant) As String
  If IsNull(Tieto) Or Tieto = vbNullString Then
    Arvo = vbNullChar
  Else
    Arvo = Tieto
  End If
End Function
Private Function DoubleToPoint(ByVal Piste As Double) As String
Dim apu As String
Dim Osoitin As Integer
  apu = CStr(Piste)
  Osoitin = InStr(apu, ",")
  If Osoitin = 0 Then
    DoubleToPoint = apu
  Else
    DoubleToPoint = Left(apu, Osoitin - 1) & "." & Mid(apu, Osoitin + 1)
  End If
End Function
Private Function AddDonut(space As AcadBlock, inRad As Double, outRad As Double, cenPt As Variant) As AcadLWPolyline

    Dim width As Double, radius As Double
    Dim tmp, v(3) As Double, pl As AcadLWPolyline
    Dim PI As Double
    
    PI = Atn(1) * 4
    width = (outRad - inRad) / 2
    radius = (inRad + width) / 2
    tmp = ThisDrawing.Utility.PolarPoint(cenPt, PI, radius)
    v(0) = tmp(0): v(1) = tmp(1)
    tmp = ThisDrawing.Utility.PolarPoint(cenPt, 0, radius)
    v(2) = tmp(0): v(3) = tmp(1)
    Set pl = space.AddLightWeightPolyline(v)
    With pl
        .Closed = True
        .SetWidth 0, width, width
        .SetBulge 0, -1
        .SetWidth 1, width, width
        .SetBulge 1, -1
    End With
    
    Set AddDonut = pl

End Function
Private Sub VOffset_MouseDown(ByVal Button As Integer, ByVal Shift As Integer, ByVal X As Single, ByVal Y As Single)
Dim xtype(0 To 1) As Integer
Dim XData(0 To 1) As Variant

If Nakymat.Value <> "" Then
  Dim Offset As String
  Dim OffsetArvo As Double
  Offset = VOffset.Value
  Offset = InputBox("Give Offset for the selected view.", "Set Offset", Offset)
  If Offset <> "" Then
    OffsetArvo = CDbl(Replace(Offset, ".", ","))
    VOffset.Value = CStr(OffsetArvo)
    xtype(0) = 1001: XData(0) = "POSITIONING"
    xtype(1) = 1040: XData(1) = OffsetArvo
    ThisDrawing.Views(Nakymat.Value).SetXData xtype, XData
  End If
Else
  MsgBox "Select named view first!", vbInformation, "Set Offset"
End If
End Sub

Attribute VB_Name = "Start"
' --- 64-bitti korjattu: PtrSafe lisatty kaikkiin Declare-lauseisiin ---
' --------- [ CHOOSE FILE ] -----------------
Declare PtrSafe Function GetOpenFileName Lib "comdlg32.dll" Alias "GetOpenFileNameA" (pOpenfilename As OPENFILENAME) As Long
Declare PtrSafe Function FindWindow Lib "User32" Alias "FindWindowA" (ByVal lpClassName As Any, ByVal lpWindowName As Any) As LongPtr
Public Type OPENFILENAME
    lStructSize As Long
    hwndOwner As LongPtr
    hInstance As LongPtr
    lpstrFilter As String
    lpstrCustomFilter As String
    nMaxCustFilter As Long
    nFilterIndex As Long
    lpstrFile As String
    nMaxFile As Long
    lpstrFileTitle As String
    nMaxFileTitle As Long
    lpstrInitialDir As String
    lpstrTitle As String
    flags As Long
    nFileOffset As Integer
    nFileExtension As Integer
    lpstrDefExt As String
    lCustData As Long
    lpfnHook As Long
    lpTemplateName As String
End Type
Public DB As New ADODB.Connection
Public TauluLoops As New ADODB.Recordset
Public TauluMotors As New ADODB.Recordset
Public TauluINSTTAG As New ADODB.Recordset
Public Tietokanta As String
Public StartOK As Boolean
Sub StartPosi()
  StartOK = False
  StartForm.Show
  If StartOK Then MainForm.Show
End Sub

Attribute VB_Name = "StartForm"
Attribute VB_Base = "0{E0AA5A47-CDC8-4979-A3BB-C5833344C004}{0438378E-E5C9-4162-8C99-85F2966A252B}"
Attribute VB_GlobalNameSpace = False
Attribute VB_Creatable = False
Attribute VB_PredeclaredId = True
Attribute VB_Exposed = False
Attribute VB_TemplateDerived = False
Attribute VB_Customizable = False


Private Sub CommandButton1_Click()
Dim TAULU As New ADODB.Recordset
  If Dir(Tietokannat.Value) <> "" Then
    Tietokanta = Tietokannat.Value
    DB.Open "Driver=Microsoft Access Driver (*.mdb);DBQ=" & Tietokanta & ";"
    DB.CursorLocation = adUseClient

    On Error GoTo Virhe
    Set TAULU = DB.Execute("Select * From _InsertedToAcad")
    Set TAULU = Nothing
    StartOK = True
    Unload Me
    Exit Sub
Virhe:
    Tietokannat.BackColor = RGB(255, 150, 150)
    MsgBox "Database: " & vbCrLf & Tietokannat.Value & vbCrLf & _
           "did not contain necessary tables!", vbCritical, "Error!"
    Tietokannat.SetFocus
    Err.Clear
    Set TAULU = Nothing
    Exit Sub
  Else 'Tietokantaa ei löytynyt
    Tietokannat.BackColor = RGB(255, 150, 150)
    MsgBox "Database: " & vbCrLf & Tietokannat.Value & vbCrLf & "did not found!", vbCritical, "Error!"
    Tietokannat.SetFocus
  End If
End Sub
Private Sub CommandButton2_Click()
  Set DB = Nothing
  Unload Me
End Sub
Private Sub CommandButton3_Click()
'Tämä valitsee tiedoston hakemistosta
    Dim OpenFile As OPENFILENAME
    Dim lReturn As Long
    Dim Filtteri As String
    Dim AHakem As String
    Dim Otsikko As String
    Dim WHandle As Long
    
    WHandle = FindWindow(0&, "Interlocking")
    AHakem = "L:\Projdata\"
    
    Filtteri = "MS Access Database (*.mdb)" & Chr(0) & "*.MDB" & Chr(0)
    Otsikko = "Choose Database"
    With OpenFile
      .lStructSize = Len(OpenFile)
      .hwndOwner = WHandle
      .hInstance = 0
      .lpstrFilter = Filtteri
      .nFilterIndex = 1
      .lpstrFile = String(257, 0)
      .nMaxFile = Len(.lpstrFile) - 1
      .lpstrFileTitle = .lpstrFile
      .nMaxFileTitle = .nMaxFile
      .lpstrInitialDir = AHakem
      .lpstrTitle = Otsikko
      .flags = 0
    End With
    lReturn = GetOpenFileName(OpenFile)
    If lReturn = 0 Then
        'Painettiin Cancel painiketta. Ei tehdä mitään
    Else 'Otetaan ylös Tiedostonimi ja Hakemisto
      Tietokannat.AddItem Mid(OpenFile.lpstrFile, 1, InStr(OpenFile.lpstrFile, Chr(0)) - 1)
      Tietokannat.ListIndex = Tietokannat.ListCount - 1
    End If
End Sub
Private Sub UserForm_Initialize()
  Tietokannat.AddItem "P:\Projekti\Ripasa\Database\Instru.mdb"
  Tietokannat.AddItem "N:\whldata\Projekti\Veracel\SAHKO\DATABASE\Instru.mdb"
  Tietokannat.AddItem "N:\whldata\Projekti\Bohui\Sahko\Database\Instru.mdb"
'  Tietokannat.AddItem "L:\Projdata\Stendal\Database\Interlocking.mdb"
  Tietokannat.ListIndex = 0
End Sub
