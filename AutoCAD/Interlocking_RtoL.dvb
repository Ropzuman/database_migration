Attribute VB_Name = "ApuForm"
Attribute VB_Base = "0{638FD3C7-C7FA-4DE1-83F0-89A1EE6FC9BC}{F1A8001B-C363-4FA4-9CC1-069FF244DDC6}"
Attribute VB_GlobalNameSpace = False
Attribute VB_Creatable = False
Attribute VB_PredeclaredId = True
Attribute VB_Exposed = False
Attribute VB_TemplateDerived = False
Attribute VB_Customizable = False





Private Sub CommandButton2_Click()
  AppActivate Application.Caption 'Vain tällä tavoin voidaan katkaista mahdollinen Zoom komento
  SendKeys "{Esc}{Esc}", True
  ApuForm.Hide
  MainForm.Show
End Sub

Attribute VB_Name = "LineForm"
Attribute VB_Base = "0{0EFF7959-C77E-4C8D-8241-9673AD88EEB3}{702BBE52-57C9-4C3A-AE61-BAA74656E5F6}"
Attribute VB_GlobalNameSpace = False
Attribute VB_Creatable = False
Attribute VB_PredeclaredId = True
Attribute VB_Exposed = False
Attribute VB_TemplateDerived = False
Attribute VB_Customizable = False

Dim EkaViiva As AcadLine
Dim ViimViiva As AcadLine
Dim Valmis As Boolean
Const Pi = 3.14159265358979
Private Sub NoSymbol_Click()
  Valmis = False
  LineForm.Hide
  If LinkkiFormi Then
    LinkForm.Show
  Else
    MainForm.Show
  End If
End Sub
Private Sub OK_Click() 'Piirretään nuoli tai muu symboli viivan päähän
Dim Lyhennys As Double
Dim iPoint(2) As Double
Dim LoppuPiste(2) As Double
Dim Rotation As Double
If ARROW Then 'Nuoli
  BName = BLOCKPATH & "ARROW.DWG"
  Lyhennys = 7.5
ElseIf NOTARROW Then 'Nuli ja Not merkki
  BName = BLOCKPATH & "NOTARROW.DWG"
  Lyhennys = 7.5
Else 'Piste
  BName = BLOCKPATH & "POINT.DWG"
  Lyhennys = 0
End If
If LStart Then
  With EkaViiva
    iPoint(0) = .StartPoint(0)
    iPoint(1) = .StartPoint(1)
    Rotation = .Angle + Pi
    LoppuPiste(0) = .StartPoint(0) + Lyhennys * Cos(Rotation - Pi)
    LoppuPiste(1) = .StartPoint(1) + Lyhennys * Sin(Rotation - Pi)
    .StartPoint = LoppuPiste
  End With
Else
  With ViimViiva
    iPoint(0) = .EndPoint(0)
    iPoint(1) = .EndPoint(1)
    Rotation = .Angle
    LoppuPiste(0) = .EndPoint(0) - Lyhennys * Cos(Rotation)
    LoppuPiste(1) = .EndPoint(1) - Lyhennys * Sin(Rotation)
    .EndPoint = LoppuPiste
  End With
End If
ThisDrawing.ModelSpace.InsertBlock iPoint, BName, 1, 1, 1, Rotation
Valmis = False
Set EkaViiva = Nothing
Set ViimViiva = Nothing
LineForm.Hide
  If LinkkiFormi Then
    LinkForm.Show
  Else
    MainForm.Show
  End If
End Sub
Private Sub UserForm_Activate()
Dim iPoint As Variant
Dim sPoint(2) As Double
Dim i As Integer
If Valmis = False Then
  On Error Resume Next
  LineForm.Hide
  ThisDrawing.ActiveLayer = ThisDrawing.Layers("0")
  For i = 0 To ThisDrawing.Layers.Count - 1
    If ThisDrawing.Layers(i).Name = "CANVAS" Then
      ThisDrawing.ActiveLayer = ThisDrawing.Layers(i)
      Exit For
    End If
  Next i
  iPoint = ThisDrawing.Utility.GetPoint(, "Set start point")
  If Err = 0 Then
    sPoint(0) = iPoint(0)
    sPoint(1) = iPoint(1)
    Do
      iPoint = ThisDrawing.Utility.GetPoint(sPoint, "Set end point or end drawing")
      If Err <> 0 Then
        If ViimViiva Is Nothing Then 'Lopetettiin ennen kuin yhtäkään viiva oli piirretty
          If LinkkiFormi Then
            LinkForm.Show
          Else
            MainForm.Show
          End If
        Else
          Valmis = True
          LineForm.Show
        End If
        Exit Do
      Else
        Set ViimViiva = ThisDrawing.ModelSpace.AddLine(sPoint, iPoint)
        If EkaViiva Is Nothing Then
          Set EkaViiva = ViimViiva
        End If
        sPoint(0) = iPoint(0)
        sPoint(1) = iPoint(1)
      End If
    Loop
  Else 'Keskeytettiin heti
    If LinkkiFormi Then
      LinkForm.Show
    Else
      MainForm.Show
    End If
  End If
  Err.Clear
End If
End Sub

Attribute VB_Name = "LinkForm"
Attribute VB_Base = "0{16FD8AED-F7AD-4DBF-8890-4C5E5A589D60}{3096AF32-2291-4ECC-ACD5-D875B1E3CB35}"
Attribute VB_GlobalNameSpace = False
Attribute VB_Creatable = False
Attribute VB_PredeclaredId = True
Attribute VB_Exposed = False
Attribute VB_TemplateDerived = False
Attribute VB_Customizable = False

Dim KohdeHandle As String     'Kohteen handle
Dim ARROWs() As Integer       'Muutuja kun tutkitan tulevaa signaalia (0=viiva, 1=nuoli, 2=Not nuoli,9=virhe)
Dim KohdeHandles() As String  'Kohteen handle
Dim EkaPoint(2) As Double
Dim TokaPoint(2) As Double
Dim Piirrasuunta As Boolean
Dim Nuolityyppi As Integer
Const Pi = 3.14159265358979
Private Sub MakeLinks_Click()
'Tämä yrittää tehdä linkit lukituksiin
  TeeLinkit
  MsgBox "Links made!", vbInformation, "Make Links"
End Sub
Private Sub ShowLinks_Click()
'Tämä aliohjelma etsii XDatasta linkit ja piirtää viivat linkkien välille DEBUG Layerille
  If MsgBox("Do you want arrows pointing for direction?", vbYesNo, "Show links") = vbYes Then
    Piirrasuunta = True
  Else
    Piirrasuunta = False
  End If
  PiirraLinkit
  MsgBox "Links drawn to drawing!", vbInformation, "Draw Links"
End Sub
Private Sub ShowHandles_Click()
'Tämä etsii yhteydet ja merkitsee yhteyksien päissä olevien pisteiden handlekset
  PiirraHandlet
  MsgBox "Linked handles marked to drawing!", vbInformation, "Mark Handles"
End Sub
Private Sub ShowErrors_Click()
'Tämä etsii ne attribuutit, joihin ei ole linkitetty mitään ja piirtää niiden kohdalle merkin DEBUG Layerille
  MarkUnknown
  MsgBox "Unknown attributes marked in drawing!", vbInformation, "Mark Unknown"
End Sub
Private Sub ClearButton_Click()
'Tämä tyhjentää DEBUG layerin
Dim Vastaus As VbMsgBoxResult
  Vastaus = MsgBox("Do you want to also delete DEBUG layer?", vbYesNoCancel, "Clear DEBUG layer")
  If Vastaus = vbYes Then
    ClearDEBUG True
  ElseIf Vastaus = vbNo Then
    ClearDEBUG
  End If
End Sub
Private Sub ClearX_Click()
'Tämä tuhoaa kaiken XDatan joka on liitettynä ILOCK application nimen alle
  If MsgBox("This will destroy all XData under ILOCK application name!" & vbCrLf & " Are you sure you want to do this?", vbOKCancel, "Clear XData") = vbOK Then
    TuhoaXData
  End If
End Sub
Private Sub MakeDots_Click()
'Etsii T-risteykset ja piirtää pisteen niiden leikkaukseen
  TeePisteet
End Sub
Private Sub UserForm_Initialize()
  BLOCKPATH = "L:\Projekti\Stendal\Tyo\Interlocking\Blokit\"
End Sub
Private Sub Vaihdablokit_Click()
'Insertoidaan kaikki referenssiblokit uudelleen, koska ne ovat muuttuneet
Dim oBlock As AcadBlockReference
Dim uBlock As AcadBlockReference
Dim BNames(3) As String
Dim iPoint(2) As Double
Dim i As Integer, j As Integer, ii As Integer
Dim Joukko As AcadSelectionSet
Dim FilterType(0) As Integer
Dim FilterData(0) As Variant
Dim AttAlkup As Variant
Dim AttUusi As Variant
Dim Nimi As Integer
BNames(0) = BLOCKPATH & "REF_LOG1.DWG"
BNames(1) = BLOCKPATH & "REF_LOG2.DWG"
BNames(2) = BLOCKPATH & "REF_SAMA1.DWG"
BNames(3) = BLOCKPATH & "REF_SAMA2.DWG"
For i = 0 To 3
  Set oBlock = ThisDrawing.ModelSpace.InsertBlock(iPoint, BNames(i), 1, 1, 1, 0)
  oBlock.Delete
Next i
For i = 0 To ThisDrawing.SelectionSets.Count - 1
  If ThisDrawing.SelectionSets(i).Name = "REFBLOKIT" Then
    ThisDrawing.SelectionSets(i).Delete
    Exit For
  End If
Next i
Set Joukko = ThisDrawing.SelectionSets.Add("REFBLOKIT")
FilterType(0) = 2
FilterData(0) = "REF_LOG1,REF_LOG2,REF_SAMA1,REF_SAMA2"
Joukko.Select acSelectionSetAll, , , FilterType, FilterData
For i = 0 To Joukko.Count - 1
  Set oBlock = Joukko(i)
  AttAlkup = oBlock.GetAttributes
  Set uBlock = ThisDrawing.ModelSpace.InsertBlock(oBlock.InsertionPoint, oBlock.Name, 1, 1, 1, 0)
  AttUusi = uBlock.GetAttributes
  For j = 0 To UBound(AttUusi)
    For ii = 0 To UBound(AttAlkup)
      If AttUusi(j).TagString = AttAlkup(ii).TagString Then
        AttUusi(j).TextString = AttAlkup(ii).TextString
      End If
    Next ii
  Next j
  oBlock.Delete
Next i
Joukko.Delete
ThisDrawing.Regen acActiveViewport
Set oBlock = Nothing
End Sub
Private Sub PiirraViiva_Click()
  LinkkiFormi = True
  LinkForm.Hide
  LineForm.Show
End Sub
Private Sub TeeLinkit()
Dim i As Integer
Dim oEntity As AcadEntity
Dim oBlock As AcadBlockReference
Dim Attribuutit As Variant
Dim oAttribute As AcadAttributeReference
Application.ZoomExtents
ClearDEBUG
TuhoaXData
For Each oEntity In ThisDrawing.ModelSpace   'Kierretään läpi kaikki piirustuksen elementit (viivat, blockit jne.)
  If oEntity.EntityName = "AcDbBlockReference" Then
    Set oBlock = oEntity
    If OnkoLaite(oBlock.Name) Then
      Attribuutit = oBlock.GetAttributes
      For i = 0 To UBound(Attribuutit)
        Set oAttribute = Attribuutit(i)
        With oAttribute
          If .TextString <> "" Then
            Select Case .TagString
              Case "LEFT1", "LEFT2", "LEFT3", "LEFT4", "LEFT5", "LEFT6", "LEFT7", "LEFT8"
                EkaPoint(0) = .TextAlignmentPoint(0)
                EkaPoint(1) = .TextAlignmentPoint(1) + 2.5
                TokaPoint(0) = .TextAlignmentPoint(0) - 5
                TokaPoint(1) = .TextAlignmentPoint(1) - 2.5
                EtsiLahteet
                LaitaXData oAttribute
              Case "AUTO", "MANUAL"
                EkaPoint(0) = .TextAlignmentPoint(0) - 2.5
                EkaPoint(1) = .TextAlignmentPoint(1)
                TokaPoint(0) = .TextAlignmentPoint(0) + 2.5
                TokaPoint(1) = .TextAlignmentPoint(1) - 5
                EtsiLahteet
                LaitaXData oAttribute
              Case "RIGHT1", "RIGHT2", "RIGHT3", "RIGHT4"
                EkaPoint(0) = .TextAlignmentPoint(0)
                EkaPoint(1) = .TextAlignmentPoint(1) + 2.5
                TokaPoint(0) = .TextAlignmentPoint(0) + 5
                TokaPoint(1) = .TextAlignmentPoint(1) - 2.5
                EtsiLahteet
                LaitaXData oAttribute
            End Select
          End If
        End With
      Next i
    ElseIf OnkoRefOut(oBlock.Name) Then
      SeuraaViivaa , oBlock.InsertionPoint
      ReDim ARROWs(1)
      ARROWs(0) = 0
      ReDim KohdeHandles(1)
      KohdeHandles(0) = KohdeHandle
      LaitaXData oBlock
    ElseIf OnkoJaTai(oBlock.Name) Then
      EkaPoint(0) = oBlock.InsertionPoint(0)
      EkaPoint(1) = oBlock.InsertionPoint(1) + 10
      TokaPoint(0) = oBlock.InsertionPoint(0) - 5
      TokaPoint(1) = oBlock.InsertionPoint(1)
      EtsiLahteet
      LaitaXData oBlock
    End If
  End If
Next
Set oAttribute = Nothing
Set oEntity = Nothing
Set oBlock = Nothing
End Sub
Private Function OnkoLaite(Nimi As String) As Boolean
  Select Case UCase(Nimi)
    Case "SWITCH1", "SWITCH2", "SWITCH3", "LIMITSW1", "LIMITSW2", "LOOP1", "LOOP2", "MOTOR1", "MOTOR2", "MOTOR3", "VALVE1"
      OnkoLaite = True
    Case Else
      OnkoLaite = False
  End Select
End Function
Private Function OnkoRefIn(Nimi As String) As Boolean
  Select Case UCase(Nimi)
    Case "REF_LOG1", "REF_SAMA1", "IBG"
      OnkoRefIn = True
    Case Else
      OnkoRefIn = False
  End Select
End Function
Private Function OnkoRefOut(Nimi As String) As Boolean
  Select Case UCase(Nimi)
    Case "REF_LOG2", "REF_SAMA2"
      OnkoRefOut = True
    Case Else
      OnkoRefOut = False
  End Select
End Function
Private Function OnkoJaTai(Nimi As String) As Boolean
  Select Case Nimi
    Case "AND", "OR", "OFFDELAY", "ONDELAY", "ONOFFDELAY", "PULSE1", "SR", "RS"
      OnkoJaTai = True
    Case Else
      OnkoJaTai = False
  End Select
End Function
Private Sub EtsiLahteet()
Dim Joukko As AcadSelectionSet
Dim oEntity As AcadEntity
Dim oBlock As AcadBlockReference
Dim i As Integer
ReDim ARROWs(0)
ReDim KohdeHandles(0)
  For i = 0 To ThisDrawing.SelectionSets.Count - 1
    If ThisDrawing.SelectionSets(i).Name = "SSET" Then
      ThisDrawing.SelectionSets(i).Delete
      Exit For
    End If
  Next i
  Set Joukko = ThisDrawing.SelectionSets.Add("SSET")
  Joukko.Select acSelectionSetCrossing, EkaPoint, TokaPoint
  PiirraNelio
  For Each oEntity In Joukko
    If oEntity.EntityName = "AcDbBlockReference" Then
      Set oBlock = oEntity
      If oBlock.Name = "ARROW" Then
        ARROWs(UBound(ARROWs)) = 1
        ReDim Preserve ARROWs(UBound(ARROWs) + 1)
        SeuraaViivaa oBlock
        KohdeHandles(UBound(KohdeHandles)) = KohdeHandle
        ReDim Preserve KohdeHandles(UBound(KohdeHandles) + 1)
      ElseIf oBlock.Name = "NOTARROW" Then
        ARROWs(UBound(ARROWs)) = 2
        ReDim Preserve ARROWs(UBound(ARROWs) + 1)
        SeuraaViivaa oBlock
        KohdeHandles(UBound(KohdeHandles)) = KohdeHandle
        ReDim Preserve KohdeHandles(UBound(KohdeHandles) + 1)
      End If
    ElseIf oEntity.EntityName = "AcDbLine" Then
      ARROWs(UBound(ARROWs)) = 0
      ReDim Preserve ARROWs(UBound(ARROWs) + 1)
      KohdeHandles(UBound(KohdeHandles)) = ""
      ReDim Preserve KohdeHandles(UBound(KohdeHandles) + 1)
    End If
  Next
  Joukko.Delete
  Set oBlock = Nothing
  Set Joukko = Nothing
End Sub
Private Sub LaitaXData(Objekti As AcadEntity)
Dim SIGNAALI(2) As String
Dim XData() As Variant
Dim XType() As Integer
Dim Koko As Integer
Dim i As Integer, j As Integer
If UBound(ARROWs) > 0 Then
  Koko = (UBound(ARROWs)) * 2
  SIGNAALI(0) = "LINE"
  SIGNAALI(1) = "ARROW"
  SIGNAALI(2) = "NOTARROW"
  ReDim XType(Koko)
  ReDim XData(Koko)
  XType(0) = 1001: XData(0) = "ILOCK"      'Sovellusnimi
  j = 1
  For i = 0 To UBound(ARROWs) - 1
    XType(j) = 1000: XData(j) = SIGNAALI(ARROWs(i))       'Signaalin tyyppi joka kyseiseen attribuuttiin tulee
    XType(j + 1) = 1005: XData(j + 1) = KohdeHandles(i)   'Sen blokin/attribuutin handles, joka lukitsee
    j = j + 2
  Next i
  Objekti.SetXData XType, XData
End If
End Sub
Private Sub ClearDEBUG(Optional Tuhoa As Boolean) 'Muodostaa tai tyhjentää DEBUG layerin tai tuhoaa sen
Dim Joukko As AcadSelectionSet
Dim FilterType(0) As Integer
Dim FilterData(0) As Variant
Dim i As Integer
Application.ZoomExtents
TeeDEBUG
For i = 0 To ThisDrawing.SelectionSets.Count - 1
  If ThisDrawing.SelectionSets(i).Name = "DELETE" Then
    ThisDrawing.SelectionSets(i).Delete
  End If
Next i
Set Joukko = ThisDrawing.SelectionSets.Add("DELETE")
FilterType(0) = 8       'Type 8 = Layer
FilterData(0) = "DEBUG" 'Layer name
Joukko.Select acSelectionSetAll, , , FilterType, FilterData
Joukko.Erase
Joukko.Delete
If Tuhoa Then
  ThisDrawing.ActiveLayer = ThisDrawing.Layers("0")
  ThisDrawing.Layers("DEBUG").Delete
End If
Set Joukko = Nothing
End Sub
Private Sub TeeDEBUG()
Dim i As Integer
Dim Kerros As AcadLayer
For i = 0 To ThisDrawing.Layers.Count - 1
  If ThisDrawing.Layers(i).Name = "DEBUG" Then
    Set Kerros = ThisDrawing.Layers(i)
    Exit For
  End If
Next i
If Kerros Is Nothing Then
  Set Kerros = ThisDrawing.Layers.Add("DEBUG")
  Kerros.Color = acGreen
End If
ThisDrawing.ActiveLayer = Kerros
Set Kerros = Nothing
End Sub
Private Sub PiirraNelio()
'Piirtää polylinella nelion jossa kulmina on EkaPoin ja TokaPoint
Dim Points(14) As Double
Dim oLine As AcadPolyline
  Points(0) = EkaPoint(0): Points(1) = EkaPoint(1): Points(2) = 0
  Points(3) = EkaPoint(0): Points(4) = TokaPoint(1): Points(5) = 0
  Points(6) = TokaPoint(0): Points(7) = TokaPoint(1): Points(8) = 0
  Points(9) = TokaPoint(0): Points(10) = EkaPoint(1): Points(11) = 0
  Points(12) = EkaPoint(0): Points(13) = EkaPoint(1): Points(14) = 0
  Set oLine = ThisDrawing.ModelSpace.AddPolyline(Points)
  oLine.Color = acRed
  Set oLine = Nothing
End Sub
Private Sub SeuraaViivaa(Optional Blokki As AcadBlockReference, Optional AlkuPiste As Variant)
'Tämän aliohjelman tarkoituksena on seurata nuoliblokkiin kiinnitettyä viivaa sen lähteeseen
Dim Joukko As AcadSelectionSet
Dim Viiva As AcadLine
Dim ApuViiva As AcadLine
Dim oBlock As AcadBlockReference
Dim i As Integer, j As Integer
Dim ViivaLoytyi As Boolean
Dim BlockLoytyi As Boolean
Dim NuoliLoytyi As Boolean
Dim Attribuutit As Variant
Dim oAttribute As AcadAttributeReference
Dim TPoint(2) As Double
Dim sPoint(2) As Double
Dim Lyhin As Double
Dim ApuVali As Double
Dim Alkuun As Boolean
Dim VanhaHandle As String
KohdeHandle = ""
NuoliLoytyi = False
If Not Blokki Is Nothing Then
With Blokki
    sPoint(0) = .InsertionPoint(0) - Cos(.Rotation) * 7.5
    sPoint(1) = .InsertionPoint(1) - Sin(.Rotation) * 7.5
  End With
Else
  sPoint(0) = AlkuPiste(0)
  sPoint(1) = AlkuPiste(1)
End If
EkaPoint(0) = sPoint(0) - 1.24 '1.25
EkaPoint(1) = sPoint(1) - 1.24 '1.25
TokaPoint(0) = sPoint(0) + 1.24 '1.25
TokaPoint(1) = sPoint(1) + 1.24 '1.25
For i = 0 To ThisDrawing.SelectionSets.Count - 1
  If ThisDrawing.SelectionSets(i).Name = "SEURAA" Then
     ThisDrawing.SelectionSets(i).Delete
     Exit For
  End If
Next i
Set Joukko = ThisDrawing.SelectionSets.Add("SEURAA")
Joukko.Select acSelectionSetCrossing, EkaPoint, TokaPoint
For i = 0 To Joukko.Count - 1 'Etsitään joukosta ensimmäinen viiva
  If Joukko(i).EntityName = "AcDbLine" Then
    Set Viiva = Joukko(i)
    Alkuun = OnkoAlueella(Viiva.EndPoint)
    Exit For
  End If
Next i
Joukko.Delete
PiirraNelio
Do 'Seurataan sitten viivaa sen lähtösuuntaan
  If Alkuun Then 'Seurataan viivaa sen alkuun päin
    TPoint(0) = Viiva.StartPoint(0)
    TPoint(1) = Viiva.StartPoint(1)
  Else
    TPoint(0) = Viiva.EndPoint(0)
    TPoint(1) = Viiva.EndPoint(1)
  End If
  EkaPoint(0) = TPoint(0) + 1.24 '1.25
  EkaPoint(1) = TPoint(1) + 1.24 '1.25
  TokaPoint(0) = TPoint(0) - 1.24 '1.25
  TokaPoint(1) = TPoint(1) - 1.24 '1.25
  PiirraNelio
  Set Joukko = ThisDrawing.SelectionSets.Add("SEURAA")
  Joukko.Select acSelectionSetCrossing, EkaPoint, TokaPoint
  ViivaLoytyi = False
  BlockLoytyi = False
  VanhaHandle = Viiva.Handle
  For i = 0 To Joukko.Count - 1 'Tsekataan kaikki entityt viivan päästi
    If Joukko(i).Layer <> "DEBUG" Then 'Debug tasaolla olevia entityjä ei huomioida
      If Joukko(i).EntityName = "AcDbLine" Then 'Joukosta löytyi Viiva
        If Joukko(i).Handle <> VanhaHandle Then 'Viiva ei ole sama kuin mitä tutkitaan
          Set Viiva = Joukko(i)
          If OnkoAlueella(Viiva.EndPoint) Then
            Alkuun = True
          ElseIf OnkoAlueella(Viiva.StartPoint) Then
            Alkuun = False
          End If
'          Alkuun = OnkoAlueella(Viiva.EndPoint)
          ViivaLoytyi = True
        End If
      ElseIf Joukko(i).EntityName = "AcDbBlockReference" Then 'Löytyi blokki
        If BlockLoytyi = False Then 'Ei ole vielä löytynyt laite tai ja/tai blokkia tästä joukosta
          Set oBlock = Joukko(i)
          If OnkoLaite(oBlock.Name) Or OnkoRefIn(oBlock.Name) Or OnkoJaTai(oBlock.Name) Then 'Oikean tyyppinen blokki löytyi
            BlockLoytyi = True
          ElseIf oBlock.Name = "ARROW" Or oBlock.Name = "NOTARROW" Or OnkoRefOut(oBlock.Name) Then
            If NuoliLoytyi Then 'Jo toinen nuoli loytyi, joten jossain on virhe, lopetetaan looppi
              Exit Do
            Else
              NuoliLoytyi = True
            End If
          End If
        End If
      End If
    End If
  Next i
  Joukko.Delete
  If BlockLoytyi Then 'Löydettiin blokki, josta etsitään Handle
    If OnkoLaite(oBlock.Name) Then 'Blokki josta etsitään lähin attribuutti
      EkaPoint(0) = TPoint(0)
      EkaPoint(1) = TPoint(1)
      KohdeHandle = ""
      Attribuutit = oBlock.GetAttributes
      Lyhin = 10000
      For j = 0 To UBound(Attribuutit)
        Set oAttribute = Attribuutit(j)
        If oAttribute.TextString <> "" Then
          TokaPoint(0) = oAttribute.TextAlignmentPoint(0)
          TokaPoint(1) = oAttribute.TextAlignmentPoint(1)
          ApuVali = LaskeVali
          If ApuVali < Lyhin Then
            Lyhin = ApuVali
            KohdeHandle = oAttribute.Handle
          End If
        End If
      Next j
    ElseIf OnkoJaTai(oBlock.Name) Or OnkoRefIn(oBlock.Name) Then
      KohdeHandle = oBlock.Handle
    End If
    Exit Do 'Finaali kohde löytyi, joten ei jatketa enempää viivan seuraamista
  ElseIf ViivaLoytyi Then 'Ei löytynyt blokki, mutta löytyi viiva, joten Looppi saa jatkua
  ElseIf NuoliLoytyi Then 'Ei löytynyt blokkia tai viivaa, mutta nuoli löytyi, joten kokeillaan toiseen suuntaan
    Alkuun = Not Alkuun
  Else 'Toisesta päästä ei löytynyt viivaa eikä blokkia, joten poistutaan
    Exit Do
  End If
Loop
Set oAttribute = Nothing
Set oBlock = Nothing
Set Joukko = Nothing
Set Viiva = Nothing
End Sub
Private Function OnkoAlueella(iPoint As Variant) As Boolean
Dim XOK As Boolean
Dim YOK As Boolean
  If EkaPoint(0) > TokaPoint(0) Then
    If iPoint(0) > TokaPoint(0) And iPoint(0) < EkaPoint(0) Then
      XOK = True
    End If
  Else
    If iPoint(0) < TokaPoint(0) And iPoint(0) > EkaPoint(0) Then
      XOK = True
    End If
  End If
  If EkaPoint(1) > TokaPoint(1) Then
    If iPoint(1) > TokaPoint(1) And iPoint(1) < EkaPoint(1) Then
      YOK = True
    End If
  Else
    If iPoint(1) < TokaPoint(1) And iPoint(1) > EkaPoint(1) Then
      YOK = True
    End If
  End If
  If XOK And YOK Then
    OnkoAlueella = True
  Else
    OnkoAlueella = False
  End If
End Function
Private Sub PiirraLinkit()
Dim i As Integer
Dim oEntity As AcadEntity
Dim oKohde As AcadEntity
Dim oBlock As AcadBlockReference
Dim oAttribute As AcadAttributeReference
Dim Attribuutit As Variant
Application.ZoomExtents
TeeDEBUG 'Varmistetaan että DEBUG on olemassa ja että se on valittu
For Each oEntity In ThisDrawing.ModelSpace   'Kierretään läpi kaikki piirustuksen elementit (viivat, blockit jne.)
  If oEntity.EntityName = "AcDbBlockReference" Then
    Set oBlock = oEntity
    If OnkoLaite(oBlock.Name) Then
      Attribuutit = oBlock.GetAttributes
      For i = 0 To UBound(Attribuutit)
        Set oAttribute = Attribuutit(i)
        With oAttribute
          If .TextString <> "" Then
            PiirraViivat oAttribute
          End If
        End With
      Next i
    ElseIf OnkoJaTai(oBlock.Name) Or OnkoRefOut(oBlock.Name) Then
      PiirraViivat , oBlock
    End If
  End If
Next
Set oAttribute = Nothing
Set oEntity = Nothing
Set oBlock = Nothing
End Sub
Private Sub PiirraHandlet()
Dim i As Integer
Dim oEntity As AcadEntity
Dim oKohde As AcadEntity
Dim oBlock As AcadBlockReference
Dim oAttribute As AcadAttributeReference
Dim Attribuutit As Variant
Application.ZoomExtents
TeeDEBUG 'Varmistetaan että DEBUG on olemassa ja että se on valittu
For Each oEntity In ThisDrawing.ModelSpace   'Kierretään läpi kaikki piirustuksen elementit (viivat, blockit jne.)
  If oEntity.EntityName = "AcDbBlockReference" Then
    Set oBlock = oEntity
    If OnkoLaite(oBlock.Name) Then
      Attribuutit = oBlock.GetAttributes
      For i = 0 To UBound(Attribuutit)
        Set oAttribute = Attribuutit(i)
        With oAttribute
          If .TextString <> "" Then
            PiirraHandle oAttribute
          End If
        End With
      Next i
    ElseIf OnkoJaTai(oBlock.Name) Then
      PiirraHandle , oBlock
    End If
  End If
Next
Set oAttribute = Nothing
Set oEntity = Nothing
Set oBlock = Nothing
End Sub
Private Sub PiirraHandle(Optional Attribuutti As AcadAttributeReference, Optional Blokki As AcadBlockReference)
Dim XDataType As Variant
Dim XDataValue As Variant
Dim oKohde As AcadEntity
Dim oAttribute As AcadAttributeReference
Dim oBlock As AcadBlockReference
Dim Ympyra As AcadCircle
Dim Kahva As String
Dim i  As Integer
On Error Resume Next
  If Blokki Is Nothing Then
    EkaPoint(0) = Attribuutti.TextAlignmentPoint(0)
    EkaPoint(1) = Attribuutti.TextAlignmentPoint(1)
    Attribuutti.GetXData "ILOCK", XDataType, XDataValue
    Kahva = Attribuutti.Handle
  Else
    EkaPoint(0) = Blokki.InsertionPoint(0)
    EkaPoint(1) = Blokki.InsertionPoint(1)
    Blokki.GetXData "ILOCK", XDataType, XDataValue
    Kahva = Blokki.Handle
  End If
  If Not IsEmpty(XDataValue) Then
    For i = 0 To UBound(XDataValue)
      If XDataType(i) = 1005 Then
        If XDataValue(i) <> 0 Then
          HandleMerkki EkaPoint, Kahva
          Set oKohde = ThisDrawing.HandleToObject(XDataValue(i)) 'Haetaan Entity sen handleksen perusteella
          If oKohde.ObjectName = "AcDbBlockReference" Then
            Set oBlock = oKohde
            HandleMerkki oBlock.InsertionPoint, oBlock.Handle
          ElseIf oKohde.ObjectName = "AcDbAttribute" Then
            Set oAttribute = oKohde
            HandleMerkki oAttribute.TextAlignmentPoint, oAttribute.Handle
          End If
        End If
      End If
    Next i
  End If
  XDataType = Empty
  XDataValue = Empty
  Set oBlock = Nothing
  Set oKohde = Nothing
  Set oAttribute = Nothing
End Sub
Private Sub HandleMerkki(iPoint As Variant, Kahva As String)
Dim sPoint(2) As Double
Dim ePoint(2) As Double
Dim Viiva As AcadLine
Dim Teksti As AcadText
 sPoint(0) = iPoint(0)
 sPoint(1) = iPoint(1)
 ePoint(0) = iPoint(0) + 10
 ePoint(1) = iPoint(1) + 20
 Set Viiva = ThisDrawing.ModelSpace.AddLine(sPoint, ePoint)
 Viiva.Color = acYellow
 sPoint(0) = ePoint(0) + 20
 sPoint(1) = ePoint(1)
 Set Viiva = ThisDrawing.ModelSpace.AddLine(sPoint, ePoint)
 Viiva.Color = acYellow
 ePoint(1) = ePoint(1) + 0.5
 Set Teksti = ThisDrawing.ModelSpace.AddText(Kahva, ePoint, 3)
 Teksti.Color = acYellow
 Teksti.StyleName = "STANDARD"
 Set Viiva = Nothing
 Set Teksti = Nothing
End Sub
Private Sub PiirraViivat(Optional Attribuutti As AcadAttributeReference, Optional Blokki As AcadBlockReference)
Dim XDataType As Variant
Dim XDataValue As Variant
Dim oKohde As AcadEntity
Dim oAttribute As AcadAttributeReference
Dim oBlock As AcadBlockReference
Dim Ympyra As AcadCircle
Dim i  As Integer
On Error GoTo Virhe
  If Blokki Is Nothing Then
    EkaPoint(0) = Attribuutti.TextAlignmentPoint(0)
    EkaPoint(1) = Attribuutti.TextAlignmentPoint(1)
    Attribuutti.GetXData "ILOCK", XDataType, XDataValue
  Else
    EkaPoint(0) = Blokki.InsertionPoint(0)
    EkaPoint(1) = Blokki.InsertionPoint(1)
    Blokki.GetXData "ILOCK", XDataType, XDataValue
  End If
  If Not IsEmpty(XDataValue) Then
    For i = 0 To UBound(XDataValue)
      If XDataType(i) = 1000 Then
        If XDataValue(i) = "ARROW" Then
          Nuolityyppi = 1
        Else
          Nuolityyppi = 0
        End If
      ElseIf XDataType(i) = 1005 Then
        If XDataValue(i) <> 0 Then
          Set oKohde = ThisDrawing.HandleToObject(XDataValue(i)) 'Haetaan Entity sen handleksen perusteella
          If oKohde.ObjectName = "AcDbBlockReference" Then
            Set oBlock = oKohde
            TokaPoint(0) = oBlock.InsertionPoint(0)
            TokaPoint(1) = oBlock.InsertionPoint(1)
          Else
            Set oAttribute = oKohde
            TokaPoint(0) = oAttribute.TextAlignmentPoint(0)
            TokaPoint(1) = oAttribute.TextAlignmentPoint(1)
          End If
          PiirraArc
        End If
      End If
    Next i
  End If
Ulos:
  XDataType = Empty
  XDataValue = Empty
  Set oBlock = Nothing
  Set oKohde = Nothing
  Set oAttribute = Nothing
  Exit Sub
Virhe:
  Err.Clear
  Set Ympyra = ThisDrawing.ModelSpace.AddCircle(EkaPoint, 8)
  Ympyra.Color = acRed
  Resume Ulos
End Sub
Private Sub PiirraArc()
'Piirtää kaaren kahden pisteen välille
Dim cPoint(2) As Double
Dim Sade As Double
Dim Viiva As AcadLine
Dim aViiva As AcadLine
Dim AlkuKulma As Double
Dim LoppuKulma As Double
Dim Kaari As AcadArc
Dim kPiste As Variant
Dim oText As AcadText
If EkaPoint(0) > TokaPoint(0) Then
  cPoint(0) = TokaPoint(0) + (EkaPoint(0) - TokaPoint(0)) / 2
Else
  cPoint(0) = EkaPoint(0) + (TokaPoint(0) - EkaPoint(0)) / 2
End If
If EkaPoint(1) > TokaPoint(1) Then
  cPoint(1) = TokaPoint(1) + (EkaPoint(1) - TokaPoint(1)) / 2
Else
  cPoint(1) = EkaPoint(1) + (TokaPoint(1) - EkaPoint(1)) / 2
End If
  Set Viiva = ThisDrawing.ModelSpace.AddLine(EkaPoint, TokaPoint)
  Viiva.Rotate cPoint, Pi / 2
  Set aViiva = ThisDrawing.ModelSpace.AddLine(Viiva.EndPoint, TokaPoint)
  LoppuKulma = aViiva.Angle
  aViiva.Delete
  Set aViiva = ThisDrawing.ModelSpace.AddLine(Viiva.EndPoint, EkaPoint)
  AlkuKulma = aViiva.Angle
  Sade = aViiva.Length
  aViiva.Delete
  Set Kaari = ThisDrawing.ModelSpace.AddArc(Viiva.EndPoint, Sade, AlkuKulma, LoppuKulma)
  If Piirrasuunta Then
    kPiste = Kaari.IntersectWith(Viiva, acExtendNone)
    Set oText = ThisDrawing.ModelSpace.AddText(Nuolityyppi & ">", kPiste, 3)
    oText.Rotate kPiste, Viiva.Angle + Pi / 2
    oText.StyleName = "STANDARD"
  End If
  Viiva.Delete
  Set oText = Nothing
  Set Kaari = Nothing
  Set Viiva = Nothing
  Set aViiva = Nothing
End Sub
Private Sub MarkUnknown()
Dim i As Integer, j As Integer
Dim oEntity As AcadEntity
Dim oKohde As AcadEntity
Dim oBlock As AcadBlockReference
Dim oAttribute As AcadAttributeReference
Dim Ympyra As AcadCircle
Dim Attribuutit As Variant
Dim XDataType As Variant
Dim XDataValue As Variant
Dim Virhe As Boolean
Application.ZoomExtents
TeeDEBUG 'Varmistetaan että DEBUG on olemassa ja että se on valittu
For Each oEntity In ThisDrawing.ModelSpace   'Kierretään läpi kaikki piirustuksen elementit (viivat, blockit jne.)
  If oEntity.EntityName = "AcDbBlockReference" Then
    Set oBlock = oEntity
    If OnkoLaite(oBlock.Name) Then
      Attribuutit = oBlock.GetAttributes
      For i = 0 To UBound(Attribuutit)
        Set oAttribute = Attribuutit(i)
        With oAttribute
          Select Case .TagString
            Case "LEFT1", "LEFT2", "LEFT3", "LEFT4", "AUTO", "MANUAL", "RIGHT1", "RIGHT2", "RIGHT3", "RIGHT4"
              If .TextString <> "" Then
                oAttribute.GetXData "ILOCK", XDataType, XDataValue
                Virhe = False
                If IsEmpty(XDataValue) Then
                  Virhe = True
                End If
                If Virhe Then
                  Set Ympyra = ThisDrawing.ModelSpace.AddCircle(oAttribute.TextAlignmentPoint, 8)
                  Ympyra.Color = acYellow
                End If
              End If
          End Select
        End With
      Next i
    End If
  End If
Next
Set Ympyra = Nothing
Set oAttribute = Nothing
Set oEntity = Nothing
Set oBlock = Nothing
End Sub
Private Sub TeePisteet()
Dim i As Integer, j As Integer
Dim Viivat As AcadSelectionSet
Dim Joukko As AcadSelectionSet
Dim FilterType(0) As Integer
Dim FilterData(0) As Variant
Dim Viiva As AcadLine
Dim aViiva As AcadLine
Dim BName As String
Dim PisteLoytyi As Boolean
Dim ViivaLoytyi As Boolean
Dim iPoint(2) As Double
Dim a As Integer
Application.ZoomExtents
BName = BLOCKPATH & "POINT.DWG"
ThisDrawing.ActiveLayer = ThisDrawing.Layers("0")
For i = 0 To ThisDrawing.Layers.Count - 1
  If ThisDrawing.Layers(i).Name = "CANVAS" Then
    ThisDrawing.ActiveLayer = ThisDrawing.Layers(i)
    Exit For
  End If
Next i
For i = 0 To ThisDrawing.SelectionSets.Count - 1
  If ThisDrawing.SelectionSets(i).Name = "VIIVAT" Then
    ThisDrawing.SelectionSets(i).Delete
    Exit For
  End If
Next i
For i = 0 To ThisDrawing.SelectionSets.Count - 1
  If ThisDrawing.SelectionSets(i).Name = "SSET" Then
    ThisDrawing.SelectionSets(i).Delete
    Exit For
  End If
Next i
FilterType(0) = 0
FilterData(0) = "Line"
Set Viivat = ThisDrawing.SelectionSets.Add("VIIVAT")
Set Joukko = ThisDrawing.SelectionSets.Add("SSET")
Viivat.Select acSelectionSetAll, , , FilterType, FilterData
For i = 0 To Viivat.Count - 1 'Etsitään läpi kaikki viivat
  If Viivat(i).ObjectName = "AcDbLine" And Viivat(i).Layer <> "DEBUG" Then
    Set Viiva = Viivat(i)
'Etsitään viivan alkupäästä risteäviä viivoja
    For a = 1 To 2
      If a = 1 Then 'Etsitään ristetäviä viivoja viivan alkupäästä
        iPoint(0) = Viiva.StartPoint(0)
        iPoint(1) = Viiva.StartPoint(1)
      Else
        iPoint(0) = Viiva.EndPoint(0)
        iPoint(1) = Viiva.EndPoint(1)
      End If
      EkaPoint(0) = iPoint(0) + 1.25
      EkaPoint(1) = iPoint(1) + 1.25
      TokaPoint(0) = iPoint(0) - 1.25
      TokaPoint(1) = iPoint(1) - 1.25
      PisteLoytyi = False
      ViivaLoytyi = False
      Joukko.Clear
      Joukko.Select acSelectionSetCrossing, EkaPoint, TokaPoint
      For j = 0 To Joukko.Count - 1
        If Joukko(j).Handle <> Viiva.Handle Then
          If Joukko(j).ObjectName = "AcDbBlockReference" Then
            PisteLoytyi = True
          ElseIf Joukko(j).ObjectName = "AcDbLine" And Joukko(j).Layer <> "DEBUG" Then
            Set aViiva = Joukko(j)
            If OnkoAlueella(aViiva.EndPoint) = False And OnkoAlueella(aViiva.StartPoint) = False Then
              ViivaLoytyi = True
            End If
          End If
        End If
      Next j
      If ViivaLoytyi And PisteLoytyi = False Then 'Risteävä viiva löytyi, mutta ei pistettä sen päästä
        ThisDrawing.ModelSpace.InsertBlock iPoint, BName, 1, 1, 1, 0 'Lisätään piste
      End If
    Next a
  End If
Next i
Viivat.Delete
Joukko.Delete
Set Viiva = Nothing
Set aViiva = Nothing
Set Viivat = Nothing
Set Joukko = Nothing
End Sub
Private Function LaskeVali() As Double
'Laskee kahden pisteen välisen etäisyyden
  LaskeVali = Sqr(Abs(EkaPoint(0) - TokaPoint(0)) ^ 2 + Abs(EkaPoint(1) - TokaPoint(1)) ^ 2)
End Function
Private Sub TuhoaXData()
Dim i As Integer
Dim oEntity As AcadEntity
Dim oBlock As AcadBlockReference
Dim Attribuutit As Variant
For Each oEntity In ThisDrawing.ModelSpace   'Kierretään läpi kaikki piirustuksen elementit (viivat, blockit jne.)
  TuhoaX oEntity
  If oEntity.ObjectName = "AcDbBlockReference" Then
    Set oBlock = oEntity
    If oBlock.HasAttributes Then
      Attribuutit = oBlock.GetAttributes
      For i = 0 To UBound(Attribuutit)
        TuhoaX Attribuutit(i)
      Next i
    End If
  End If
Next
Set oEntity = Nothing
Set oBlock = Nothing
End Sub
Private Sub TuhoaX(Objekti As Variant)
Dim XDataType As Variant
Dim XDataValue As Variant
Dim DataType(0) As Integer
Dim Data(0) As Variant
Dim i  As Integer
  DataType(0) = 1001 'Type = Application name
  Data(0) = "ILOCK"  'Application name
  Objekti.GetXData "", XDataType, XDataValue
  If Not IsEmpty(XDataValue) Then
    Objekti.SetXData DataType, Data
  End If
  XDataType = Empty
  XDataValue = Empty
End Sub

Attribute VB_Name = "MainForm"
Attribute VB_Base = "0{B13937C5-9F96-4695-800A-8EB195FB2410}{6173CB65-2293-403B-AAA8-1463EBCE4E55}"
Attribute VB_GlobalNameSpace = False
Attribute VB_Creatable = False
Attribute VB_PredeclaredId = True
Attribute VB_Exposed = False
Attribute VB_TemplateDerived = False
Attribute VB_Customizable = False

Dim BASEPATH  As String
Dim SAVEPATH As String
Dim BASEDWG   As String
Dim MotorFilter As String
Dim LoopFilter As String

Private Sub Blokit_Change()
On Error Resume Next
  Preview.src = BLOCKPATH & Blokit.Value & ".dwg"
  Preview.Appearance = 1
  Preview.BackgroundColor = 2
  Preview.ZoomExtents
  Err.Clear
End Sub

Private Sub CommandButton3_Click()
  Application.Documents.Open BASEPATH & BASEDWG & ".dwg", True
  Application.ZoomExtents
End Sub

Private Sub CommandButton4_Click()
Dim Vast As String
Vast = InputBox("Give filter for loops." & _
       vbCrLf & "Eg. ""LoopNo > 3000 AND Area='411'""" & _
       vbCrLf & "or ""Area = '411' AND LoopNo='2001'""" & _
       vbCrLf & "To clear filter enter "" """, "Loop Filter", LoopFilter)
If Vast <> "" Then
  LoopFilter = Trim(Vast)
  TaytaLaitteet
End If
End Sub

Private Sub CommandButton5_Click()
Dim Vast As String
Vast = InputBox("Give filter for motors." & _
       vbCrLf & "Eg. ""LoopNo > 3000 AND Area='411'""" & _
       vbCrLf & "or ""Area = '411' AND LoopNo='2001'""" & _
       vbCrLf & "To clear filter enter "" """, "Motor Filter", MotorFilter)
If Vast <> "" Then
  MotorFilter = Trim(Vast)
  TaytaLaitteet
End If
End Sub

Private Sub DrawLine_Click()
  MainForm.Hide
  LineForm.Show
End Sub
Private Sub InsertCrossPoint_Click()
Dim gPoint As Variant
'Dim iPoint(2) As Double
Dim BName As String
'Dim Piste As String
'Dim PointBlock As AcadBlockReference
On Error GoTo Virhe 'Täytyy olla, jos GetPoint ei toimikaan
  MainForm.Hide
  ThisDrawing.SendCommand Chr(27) & Chr(27) 'Varmistetaan että ollaan poistuttu komennosta
  Do
    gPoint = ThisDrawing.Utility.GetPoint(, "Set point for dot")
    BName = BLOCKPATH & "POINT.DWG"
    ActiveDocument.ModelSpace.InsertBlock gPoint, BName, 1, 1, 1, 0
    ActiveDocument.Regen acActiveViewport
  Loop
Virhe:
  Err.Clear
  On Error GoTo 0
  Set PointBlock = Nothing
  MainForm.Show
End Sub


Private Sub LisaaMuu_Click()
Dim gPoint As Variant
Dim iPoint(2) As Double
Dim BName As String
Dim MuuBlock As AcadBlockReference
Dim Attribuutit As Variant
Dim i As Integer
Dim Piste As String
On Error GoTo Virhe 'Täytyy olla, jos GetPoint ei toimikaan
  MainForm.Hide
  ThisDrawing.SendCommand Chr(27) & Chr(27) 'Varmistetaan että ollaan poistuttu komennosta
'Käsketään klikata jotain pistettä
Virhe:
  gPoint = ThisDrawing.Utility.GetPoint(, "Set start point")
  Err.Clear
  On Error GoTo 0
  iPoint(0) = gPoint(0) + 0.00001
  iPoint(1) = gPoint(1) + 0.00001
'---------------------------------------------------------

  Piste = DoubleToPoint(CDbl(iPoint(0))) & "," & DoubleToPoint(CDbl(iPoint(1)))
  BName = BLOCKPATH & MuutBlokit.Value & ".DWG"
  ThisDrawing.SendCommand Chr(27) & Chr(27) 'Varmistetaan että ollaan poistuttu komennosta
  Set MuuBlock = ThisDrawing.ModelSpace.InsertBlock(iPoint, BName, 1, 1, 1, 0)
  If MuuBlock.HasAttributes Then
    Attribuutit = MuuBlock.GetAttributes
    For i = 0 To UBound(Attribuutit) 'Käydään läpi kaikki attribuutit
      Attribuutit(i).TextString = Controls("Attr" & i).Value
    Next i
  End If
  ThisDrawing.SendCommand "(command ""move"" ""last"" """" """ & Piste & """)" & vbCr
  With MuuBlock
    If .InsertionPoint(0) = iPoint(0) And .InsertionPoint(1) = iPoint(1) Then
      .Delete
    End If
  End With
  Set MuuBlock = Nothing
  MainForm.Show
End Sub
Private Sub Lisays_Click() 'Laitteen insertointi
Dim oBlock As AcadBlockReference
Dim BName As String
Dim iPoint(2) As Double
Dim gPoint As Variant
Dim Attribuutit As Variant
Dim i As Integer
Dim Piste As String
On Error GoTo Virhe
'Liitetään ensin blokki kuvaan
  MainForm.Hide
  ThisDrawing.SendCommand Chr(27) & Chr(27) 'Varmistetaan että ollaan poistuttu komennosta
'AutoCAD etsii itse pisteen
'  ThisDrawing.ActiveSpace = acPaperSpace
'  ThisDrawing.ActiveSpace = acModelSpace
'  iPoint(0) = ThisDrawing.ActiveViewport.Center(0)
'  iPoint(1) = ThisDrawing.ActiveViewport.Center(1)
'Käsketään klikata jotain pistettä
Virhe:
  gPoint = ThisDrawing.Utility.GetPoint(, "Set start point")
  Err.Clear
  On Error GoTo 0
  iPoint(0) = gPoint(0) + 0.00001
  iPoint(1) = gPoint(1) + 0.00001
'---------------------------------------------------------
  Piste = DoubleToPoint(CDbl(iPoint(0))) & "," & DoubleToPoint(CDbl(iPoint(1)))
  BName = BLOCKPATH & Blokit.Value & ".dwg"
  Set oBlock = ThisDrawing.ModelSpace.InsertBlock(iPoint, BName, 1, 1, 1, 0)
  Attribuutit = oBlock.GetAttributes
  For i = 0 To UBound(Attribuutit) 'Käydään läpi kaikki attribuutit
    With Attribuutit(i)
      Select Case UCase(.TagString)
        Case "POS"
          .TextString = Arvo(TPOS.Value)
        Case "INSTTAG"
          .TextString = Arvo(TINSTTAG.Value)
        Case "T_LINE_1", "T_L_1"
          .TextString = Arvo(T_L_1.Value)
        Case "T_LINE_2", "T_L_2"
          .TextString = Arvo(T_L_2.Value)
        Case "T_LINE_3", "T_L_3"
          .TextString = Arvo(T_L_3.Value)
        Case "T_LINE_4", "T_L_4"
          .TextString = Arvo(T_L_4.Value)
        Case "T_LINE_5", "T_L_5"
          .TextString = Arvo(T_L_5.Value)
        Case "R_R_1(4)"
          .TextString = Arvo(R_R_14.Value)
        Case "R_R_2(4)"
          .TextString = Arvo(R_R_24.Value)
        Case "R_R_3(4)"
          .TextString = Arvo(R_R_34.Value)
        Case "R_R_4(4)"
          .TextString = Arvo(R_R_44.Value)
        Case "R_R_1(3)"
          .TextString = Arvo(R_R_13.Value)
        Case "R_R_2(3)"
          .TextString = Arvo(R_R_23.Value)
        Case "R_R_3(3)"
          .TextString = Arvo(R_R_33.Value)
        Case "R_L_1(4)"
          .TextString = Arvo(R_L_14.Value)
        Case "R_L_2(4)"
          .TextString = Arvo(R_L_24.Value)
        Case "R_L_3(4)"
          .TextString = Arvo(R_L_34.Value)
        Case "R_L_4(4)"
          .TextString = Arvo(R_L_44.Value)
        Case "R_L_1(3)"
          .TextString = Arvo(R_L_13.Value)
        Case "R_L_2(3)"
          .TextString = Arvo(R_L_23.Value)
        Case "R_L_3(3)"
          .TextString = Arvo(R_L_33.Value)
      End Select
    End With
  Next i
  'Annetaan komentorivikomento jolla saadaan siirrettyä blokkia haluttuun paikkaan
  ThisDrawing.SendCommand "(command ""move"" ""last"" """" """ & Piste & """)" & vbCr
  With oBlock
    If .InsertionPoint(0) = iPoint(0) And .InsertionPoint(1) = iPoint(1) Then
      .Delete
    End If
  End With
  Set oBlock = Nothing
  MainForm.Show
End Sub
Private Sub LoopLaitteet_Change()
Dim Lista As Variant
Dim i As Integer
  If IsNull(LoopLaitteet.Value) = False Then
    With LoopLaitteet
      TDB_INDEX.Value = .Column(0, .ListIndex)
      TPOS.Value = .Column(1, .ListIndex)
      T_L_1.Value = .Column(3, .ListIndex)
      T_L_2.Value = .Column(4, .ListIndex)
      Set TauluINSTTAG = DB.Execute("SELECT EqTAG FROM TOACADLoopEq WHERE AreaCode='" & .Column(5, .ListIndex) & "' AND LoopNo='" & .Column(6, .ListIndex) & "'")
      TINSTTAG.Clear
      If TauluINSTTAG.EOF Then
        TINSTTAG.AddItem .Column(2, .ListIndex)
      Else
        Lista = TauluINSTTAG.GetRows()
        For i = 0 To UBound(Lista, 2)
          TINSTTAG.AddItem Lista(0, i)
        Next i
      End If
      TINSTTAG.ListIndex = 0
      TINSTTAG.Value = .Column(2, .ListIndex)
    End With
  End If
End Sub
Private Sub MotorLaitteet_Change()
  If IsNull(MotorLaitteet.Value) = False Then
    With MotorLaitteet
      TDB_INDEX.Value = .Column(0, .ListIndex)
      TPOS.Value = .Column(1, .ListIndex)
'      T_L_1.Value = .Column(3, .ListIndex)
      T_L_1.Value = .Column(4, .ListIndex)
      T_L_2.Value = .Column(5, .ListIndex)
      TINSTTAG.Clear
      TINSTTAG.AddItem .Column(2, .ListIndex)
    End With
    TINSTTAG.ListIndex = 0
  End If
End Sub
Private Sub MultiPage1_Change()
  NaytaBlokki
End Sub
Private Sub Muokkaa_Click() 'Laitteen muokkaus
Dim Valinta As AcadObject
Dim Point(0 To 2) As Double
Dim BlockNimi As String
Dim Oikea As Boolean
Dim Attribuutit As Variant
Dim i As Integer
Dim OK As Boolean
  MainForm.Hide
  ThisDrawing.SendCommand Chr(27) & Chr(27) 'Varmistetaan että ollaan poistuttu komennosta
  ThisDrawing.Utility.GetEntity Valinta, Point, "Choose Device..."
  If Valinta.ObjectName = "AcDbBlockReference" Then
    BlockNimi = UCase(Valinta.Name)
    For i = 1 To Blokit.ListRows  'Tarkistetaan että blokin nimi löytyy luettelosta
      If Blokit.List(i) = BlockNimi Then   'Löyty
        Oikea = True
        Exit For
      End If
    Next i
    If Oikea Then
      If Valinta.HasAttributes Then
        OK = True
        Attribuutit = Valinta.GetAttributes
        TaytaTextBoxit Attribuutit
      End If
    End If
  End If
  If OK = False Then
    MsgBox "Error in selecting block!", vbOKOnly, "Edit Block"
  End If
  MainForm.Show
End Sub

Private Sub MuutBlokit_Change()
On Error Resume Next
  Preview.src = BLOCKPATH & MuutBlokit.Value & ".dwg"
  Preview.Appearance = 1
  Preview.BackgroundColor = 2
  Preview.ZoomExtents
  Err.Clear
End Sub

Private Sub OBLoop_Click()
  LoopLaitteet.Visible = True
  MotorLaitteet.Visible = False
  LoopLaitteet_Change
End Sub
Private Sub OBMotor_Click()
  LoopLaitteet.Visible = False
  MotorLaitteet.Visible = True
  MotorLaitteet_Change
End Sub

Private Sub T1_Change()
  TPULSE.Value = T1.Value
End Sub

Private Sub TINSTTAG_Change()
  T_L_4.Value = TINSTTAG.Value
End Sub

Private Sub TPULSE_Change()
  T1.Value = TPULSE.Value
End Sub

Private Sub UserForm_Initialize()
Dim Asetukset As New ADODB.Recordset
'Varmistetaan ettei AutoCADissä ole komentoja päällä
AppActivate Application.Caption 'Vain tällä tavoin voidaan katkaista mahdollinen Zoom komento
SendKeys "{Esc}{Esc}", True
TauluLoops.Open "TOACAD_Loops", DB ', adOpenDynamic
TauluMotors.Open "TOACAD_Motors", DB ', adOpenDynamic

Asetukset.Open "SETTINGS", DB
Do While Not Asetukset.EOF
  Select Case UCase(Asetukset.Fields(0).Value)
    Case "BLOCK"
      Blokit.AddItem Asetukset.Fields(1).Value
    Case "BLOCK_O"
      MuutBlokit.AddItem Asetukset.Fields(1).Value
    Case "BASEPATH"
      BASEPATH = Asetukset.Fields(1).Value
    Case "BLOCKPATH"
      BLOCKPATH = Asetukset.Fields(1).Value
    Case "SAVEPATH"
      SAVEPATH = Asetukset.Fields(1).Value
    Case "BASEDWG"
      BASEDWG = Asetukset.Fields(1).Value
  End Select
  Asetukset.MoveNext
Loop
MuutBlokit.ListIndex = 0
Blokit.ListIndex = 0
Set Asetukset = Nothing
TaytaLaitteet
End Sub
Private Sub StopButton_Click()
'Ohjelman suorituksen keskeytys
  Unload Me
End Sub
Private Sub UserForm_Terminate()
  Set DB = Nothing
  Set TauluLoops = Nothing
  Set TauluMotors = Nothing
  Set TauluINSTTAG = Nothing
End Sub
Private Sub TaytaLaitteet()
On Error GoTo Virhe
TauluLoops.Filter = LoopFilter
TauluMotors.Filter = MotorFilter

LoopLaitteet.Clear
MotorLaitteet.Clear
TauluLoops.MoveFirst
TauluMotors.MoveFirst
If TauluMotors.EOF = False Then
  MotorLaitteet.Column() = TauluMotors.GetRows()
  MotorLaitteet.ListIndex = 0
End If
If TauluLoops.EOF = False Then
  LoopLaitteet.Column() = TauluLoops.GetRows()
  LoopLaitteet.ListIndex = 0
End If
Exit Sub
Virhe:
  Err.Clear
  MsgBox "Syntax error in filter.", vbCritical, "Set Filter"
End Sub
Private Sub CommandButton2_Click()
  MainForm.Hide
  ApuForm.Show
End Sub
Private Function Arvo(Tieto As Variant) As String
  If IsNull(Tieto) Or Tieto = vbNullString Then
    Arvo = vbNullChar
  Else
    Arvo = Tieto
  End If
End Function
Private Sub TaytaTextBoxit(Attribuutit As Variant)
Dim i As Integer
'Tyhjennetään ensin kaikki textBoxit
  TAUTO.Value = vbNullString
  TMANUAL.Value = vbNullString
  TPOS.Value = vbNullString
  TINSTTAG.Value = vbNullString
  TDESC1.Value = vbNullString
  TDESC2.Value = vbNullString
  TDESC3.Value = vbNullString
  TDB_INDEX.Value = vbNullString
  For i = 1 To 8
    Controls("L" & i).Value = vbNullString
    Controls("R" & i).Value = vbNullString
  Next i
  For i = 0 To UBound(Attribuutit) 'Käydään läpi kaikki blokin attribuutit
    With Attribuutit(i)
      Select Case UCase(.TagString)
        Case "POS", "INSTTAG", "DESC1", "DESC2", "DESC3", "DB_INDEX", "AUTO", "MANUAL"
          Controls("T" & .TagString).Value = .TextString
        Case "L1", "L2", "L3", "L4", "L5", "L6", "L7", "L8", "R1", "R2", "R3", "R4", "R5", "R6", "R7", "R8"
          Controls(.TagString).Value = .TextString
       End Select
    End With
  Next i
End Sub
Private Sub NaytaBlokki()
If MultiPage1.Value = 0 Then
  Blokit_Change
ElseIf MultiPage1.Value = 1 Then
  MuutBlokit_Change
End If
End Sub
Private Function DoubleToPoint(ByVal Piste As Double) As String
Dim APU As String
Dim Osoitin As Integer
  APU = CStr(Piste)
  Osoitin = InStr(APU, ",")
  If Osoitin = 0 Then
    DoubleToPoint = APU
  Else
    DoubleToPoint = Left(APU, Osoitin - 1) & "." & Mid(APU, Osoitin + 1)
  End If
End Function

Attribute VB_Name = "Start"
' --- 64-bitti korjattu: PtrSafe lisatty kaikkiin Declare-lauseisiin ---
' --------- [ CHOOSE FILE ] -----------------
Declare PtrSafe Function GetOpenFileName Lib "comdlg32.dll" Alias "GetOpenFileNameA" (pOpenfilename As OPENFILENAME) As Long
Declare PtrSafe Function FindWindow Lib "User32" Alias "FindWindowA" (ByVal lpClassName As Any, ByVal lpWindowName As Any) As LongPtr
Public Type OPENFILENAME
    lStructSize As Long
    hwndOwner As LongPtr
    hInstance As LongPtr
    lpstrFilter As String
    lpstrCustomFilter As String
    nMaxCustFilter As Long
    nFilterIndex As Long
    lpstrFile As String
    nMaxFile As Long
    lpstrFileTitle As String
    nMaxFileTitle As Long
    lpstrInitialDir As String
    lpstrTitle As String
    flags As Long
    nFileOffset As Integer
    nFileExtension As Integer
    lpstrDefExt As String
    lCustData As Long
    lpfnHook As Long
    lpTemplateName As String
End Type
Public DB As New ADODB.Connection
Public TauluLoops As New ADODB.Recordset
Public TauluMotors As New ADODB.Recordset
Public TauluINSTTAG As New ADODB.Recordset
Public Tietokanta As String
Public StartOK As Boolean
Public AreaNo As String
Public PreviewText As String
Public PreviewFile As String
Public BLOCKPATH  As String
Public LinkkiFormi As Boolean
Sub StartInterlocking()
  StartOK = False
  StartForm.Show
  If StartOK Then MainForm.Show
End Sub
Sub StartLink()
  LinkForm.Show
End Sub

Attribute VB_Name = "StartForm"
Attribute VB_Base = "0{A2D208C9-28A3-4BDD-AD79-AFB519A1C65D}{8113D5B3-4CD5-4DD2-B87B-CB645B9E1DD2}"
Attribute VB_GlobalNameSpace = False
Attribute VB_Creatable = False
Attribute VB_PredeclaredId = True
Attribute VB_Exposed = False
Attribute VB_TemplateDerived = False
Attribute VB_Customizable = False


Private Sub CommandButton1_Click()
Dim TAULU As New ADODB.Recordset
  If Dir(Tietokannat.Value) <> "" Then
    DB.Open "Driver=Microsoft Access Driver (*.mdb);DBQ=" & Tietokannat.Value & ";"
    Tietokanta = Tietokannat.Value
    On Error GoTo Virhe
    Set TAULU = DB.Execute("Select * From TOACAD")
    Set TAULU = DB.Execute("Select * From SETTINGS")
    Set TAULU = DB.Execute("Select * From TOACADLoopEq")
    Set TAULU = Nothing
    StartOK = True
    Unload Me
    Exit Sub
Virhe:
    Tietokannat.BackColor = RGB(255, 150, 150)
    MsgBox "Database: " & vbCrLf & Tietokannat.Value & vbCrLf & _
           "did not contain necessary tables (TOACAD, TOACADLoopEq AND SETTINGS)!", vbCritical, "Error!"
    Tietokannat.SetFocus
    Err.Clear
    Set TAULU = Nothing
    Exit Sub
  Else 'Tietokantaa ei löytynyt
    Tietokannat.BackColor = RGB(255, 150, 150)
    MsgBox "Database: " & vbCrLf & Tietokannat.Value & vbCrLf & "did not found!", vbCritical, "Error!"
    Tietokannat.SetFocus
  End If
End Sub
Private Sub CommandButton2_Click()
  Set DB = Nothing
  Unload Me
End Sub
Private Sub CommandButton3_Click()
'Tämä valitsee tiedoston hakemistosta
    Dim OpenFile As OPENFILENAME
    Dim lReturn As Long
    Dim Filtteri As String
    Dim AHakem As String
    Dim Otsikko As String
    Dim WHandle As Long
    
    WHandle = FindWindow(0&, "Interlocking")
    AHakem = "L:\Projdata\"
    
    Filtteri = "MS Access Database (*.mdb)" & Chr(0) & "*.MDB" & Chr(0)
    Otsikko = "Choose Database"
    With OpenFile
      .lStructSize = Len(OpenFile)
      .hwndOwner = WHandle
      .hInstance = 0
      .lpstrFilter = Filtteri
      .nFilterIndex = 1
      .lpstrFile = String(257, 0)
      .nMaxFile = Len(.lpstrFile) - 1
      .lpstrFileTitle = .lpstrFile
      .nMaxFileTitle = .nMaxFile
      .lpstrInitialDir = AHakem
      .lpstrTitle = Otsikko
      .flags = 0
    End With
    lReturn = GetOpenFileName(OpenFile)
    If lReturn = 0 Then
        'Painettiin Cancel painiketta. Ei tehdä mitään
    Else 'Otetaan ylös Tiedostonimi ja Hakemisto
      Tietokannat.AddItem Mid(OpenFile.lpstrFile, 1, InStr(OpenFile.lpstrFile, Chr(0)) - 1)
      Tietokannat.ListIndex = Tietokannat.ListCount - 1
    End If
End Sub
Private Sub UserForm_Initialize()
  Tietokannat.AddItem "K:\PROJECTS\L_PROJEKTI\Riau1_rebuild\DATABASE\Instru.mdb"
  Tietokannat.AddItem "N:\whldata\Projekti\Veracel\SAHKO\DATABASE\Instru.mdb"
  Tietokannat.AddItem "L:\Projdata\Stendal\Database\Interlocking.mdb"
  Tietokannat.ListIndex = 0
End Sub
