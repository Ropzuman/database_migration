Attribute VB_Name = "Koodi"
Sub SNappaa()
  SnappiForm.Show False
End Sub
Sub Sulje()
Dim FSO As New FileSystemObject
Dim Asema As Scripting.Drive
Dim Nimi As String
Unload SnappiForm
For Each Asema In FSO.Drives
  If Asema.IsReady Then
    If Asema.ShareName <> "" Then
      If LCase(Left(VBE.activeVBproject.Filename, Len(Asema.ShareName))) = LCase(Asema.ShareName) Then
        Nimi = Asema.Path & Mid(VBE.activeVBproject.Filename, Len(Asema.ShareName) + 1)
        Exit For
      End If
    End If
  End If
Next
Set Drive = Nothing
Set FSO = Nothing
If Nimi <> "" Then UnloadDVB Nimi
End Sub

Attribute VB_Name = "SnappiForm"
Attribute VB_Base = "0{321AB7EF-6AB8-4613-B282-4BC64565F670}{1ACCF2BA-9CB2-44B7-AD89-2AFC21C7CB07}"
Attribute VB_GlobalNameSpace = False
Attribute VB_Creatable = False
Attribute VB_PredeclaredId = True
Attribute VB_Exposed = False
Attribute VB_TemplateDerived = False
Attribute VB_Customizable = False

Private Sub OK_Click()
Dim oEntity As AcadEntity
Dim Joukko As AcadSelectionSet

Set Joukko = ActiveDocument.ActiveSelectionSet
ActiveDocument.SendCommand "SNAP " & VSnap.Value & " "
ActiveDocument.SendCommand "SNAPMODE 1 "
For Each oEntity In Joukko
  Tarkista oEntity
Next
Joukko.Delete
Set Joukko = Nothing
Set oEntity = Nothing
Sulje
End Sub
Private Sub Peruuta_Click()
  Sulje
End Sub
Private Sub Tarkista(oEntity As Object)
Dim oViiva As AcadLine
Dim oBlock As AcadBlockReference
Dim oText As AcadText
Dim oPLine As AcadPolyline
  If oEntity.ObjectName = "AcDbLine" Then
    Set oViiva = oEntity
    oViiva.StartPoint = Snappi(oViiva.StartPoint)
    oViiva.EndPoint = Snappi(oViiva.EndPoint)
  ElseIf oEntity.ObjectName = "AcDbText" Then
    Set oText = oEntity
    If oText.Alignment = 0 Then
      oText.InsertionPoint = Snappi(oText.InsertionPoint)
    Else
      oText.TextAlignmentPoint = Snappi(oText.TextAlignmentPoint)
    End If
  ElseIf oEntity.ObjectName = "AcDbBlockReference" Then
    Set oBlock = oEntity
    oBlock.InsertionPoint = Snappi(oBlock.InsertionPoint)
  ElseIf oEntity.ObjectName = "AcDb2dPolyline" Then
    Set oPLine = oEntity
    oPLine.Coordinates = Snappi(oPLine.Coordinates)
  ElseIf oEntity.ObjectName = "AcDbPolyline" Then
    oEntity.Coordinates = Snappi(oEntity.Coordinates)
  Else
  End If
  Set oViiva = Nothing
  Set oBlock = Nothing
  Set oText = Nothing
  Set oPLine = Nothing
End Sub
Private Function Snappi(Piste As Variant) As Variant
Dim iPoint() As Double
Dim i As Integer
ReDim iPoint(UBound(Piste))
  For i = 0 To UBound(Piste)
    If (Piste(i) * 100) Mod 125 = 0 Then
      iPoint(i) = Val(Piste(i) * 100) / 100
    ElseIf (Piste(i) * 1000) Mod 1250 > 625 Then
      iPoint(i) = (Val(Piste(i) * 100) + 125 - (Val(Piste(i) * 100) Mod 125)) / 100
    Else
      iPoint(i) = (Val(Piste(i) * 100) - (Val(Piste(i) * 100) Mod 125)) / 100
    End If
  Next i
  Snappi = iPoint
End Function
Private Sub UserForm_Initialize()
Dim KSnappiX As Double
Dim KSnappiY As Double
Dim KSNappi As String
  ActiveDocument.ActiveViewport.GetSnapSpacing KSnappiX, KSnappiY
  KSNappi = Replace(CStr(KSnappiX), ",", ".")
  Select Case KSNappi
    Case "1", "1.25", "2", "2.5", "5", "10", "15"
    Case Else
      VSnap.AddItem KSNappi
  End Select
  VSnap.AddItem "1"
  VSnap.AddItem "1.25"
  VSnap.AddItem "2"
  VSnap.AddItem "2.5"
  VSnap.AddItem "5"
  VSnap.AddItem "10"
  VSnap.AddItem "15"
  VSnap.Value = KSNappi
End Sub
