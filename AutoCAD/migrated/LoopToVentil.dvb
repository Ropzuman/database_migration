Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
Sub Niksu()
Dim Joukko As AcadSelectionSet
Dim i As Integer
Dim FilterType(0) As Integer
Dim FilterData(0) As Variant
Dim Apu As Object
Dim Attrib As Variant
Dim Blokki As AcadBlockReference
Dim Piste As Variant
Dim Mat As Variant
Dim Cont As Variant

Set Joukko = ActiveDocument.ActiveSelectionSet
Joukko.Clear
FilterType(0) = 2
FilterData(0) = "UP009,UP008,V20,V20C"
Joukko.Select acSelectionSetAll, , , FilterType, FilterData
For i = 0 To Joukko.Count - 1
  Set Blokki = Joukko(i)
  Application.ZoomCenter Blokki.InsertionPoint, 85
  Blokki.Highlight True
  Attrib = Blokki.GetAttributes
  If Attrib(4).TextString = "" Then
    Do
      Do
        ActiveDocument.Utility.GetSubEntity Apu, Piste, Mat, Cont, "Poimi Looppinumero"
      Loop Until Apu.ObjectName = "AcDbAttribute"
    Loop Until Apu.TagString = "CUSTPOS"
    Attrib(4).TextString = Apu.TextString
  End If
  Blokki.Highlight False
Next i

End Sub
